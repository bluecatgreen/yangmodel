module core-model {
    namespace "urn:mef:yang:core-model";
    prefix core-model;
    organization "Metro Ethernet Forum (MEF)";
    contact "MEF";
    description "none";
    revision 2017-02-27 {
        description "MEF NRP 1.0.alpha";
        reference "ONF-TR-527, ONF-TR-512, ONF-TR-531, RFC 6020 and RFC 6087";
    }
    /***********************
    * package core-network-model
    **********************/ 
        /***********************
        * package type-definitions
        **********************/ 
            identity PORT_DIRECTION {
                description "none";
            }
            identity PORT_DIRECTION_BIDIRECTIONAL {
                base port-direction;
                description "The Port has both an INPUT flow and an OUTPUT flow defined.";
            }
            identity PORT_DIRECTION_INPUT {
                base port-direction;
                description "The Port only has definition for a flow into the Forwarding entity (i.e. an ingress flow).";
            }
            identity PORT_DIRECTION_OUTPUT {
                base port-direction;
                description "The Port only has definition for a flow out of the Forwarding entity (i.e. an egress flow).";
            }
            identity PORT_DIRECTION_UNIDENTIFIED_OR_UNKNOWN {
                base port-direction;
                description "Not a normal state. The system is unable to determine the correct value.";
            }
            identity PORT_DIRECTION_OMNIDIRECTIONAL {
                base port-direction;
                description "none";
            }
            identity FORWARDING_DIRECTION {
                description "none";
            }
            identity FORWARDING_DIRECTION_BIDIRECTIONAL {
                base forwarding-direction;
                description "The Forwarding entity supports both BIDIRECTIONAL flows at all Ports (i.e. all Ports have both an INPUT flow and an OUTPUT flow defined).";
            }
            identity FORWARDING_DIRECTION_UNIDIRECTIONAL {
                base forwarding-direction;
                description "The Forwarding entity has Ports that are either INPUT or OUTPUT. It has no BIDIRECTIONAL Ports.";
            }
            identity FORWARDING_DIRECTION_UNDEFINED_OR_UNKNOWN {
                base forwarding-direction;
                description "Not a normal state. The system is unable to determine the correct value.";
            }
            identity FORWARDING_DIRECTION_OMNIDIRECTIONAL {
                base forwarding-direction;
                description "none";
            }
            identity TERMINATION_DIRECTION {
                description "none";
            }
            identity TERMINATION_DIRECTION_BIDIRECTIONAL {
                base termination-direction;
                description "A Termination with both SINK and SOURCE flows.";
            }
            identity TERMINATION_DIRECTION_SINK {
                base termination-direction;
                description "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base termination-direction;
                description "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base termination-direction;
                description "Not a normal state. The system is unable to determine the correct value.";
            }
            identity EXTENDED_TERMINATION_DIRECTION {
                description "none";
            }
            identity EXTENDED_TERMINATION_DIRECTION_CONTRA_DIRECTION_SINK {
                base extended-termination-direction;
                description "The essential flow of the Termination entity is SINK (i.e. up the layer stack) but the INPUT flow of the Termination entity was provided by a SOURCE OUTPUT or taken from a SOURCE INPUT (duplicating the input signal) hence reversing the flow orientation from down the layer stack to up the layer stack.";
            }
            identity EXTENDED_TERMINATION_DIRECTION_CONTRA_DIRECTION_SOURCE {
                base extended-termination-direction;
                description "The essential flow of the Termination entity is SOURCE (i.e. down the layer stack) but the OUTPUT flow of the Termination entity was fed to (and replaces) a SINK OUTPUT or was fed to a SINK INPUT (replacing the normal flow) hence reversing the flow orientation from down the layer stack to up the layer stack.";
            }
            identity TERMINATION_STATE {
                description "none";
            }
            identity TERMINATION_STATE_LP_CAN_NEVER_TERMINATE {
                base termination-state;
                description "A non-flexible case that can never be terminated.";
            }
            identity TERMINATION_STATE_LP_NOT_TERMINATED {
                base termination-state;
                description "A flexible termination that can terminate but is currently not terminated.";
            }
            identity TERMINATION_STATE_TERMINATED_SERVER_TO_CLIENT_FLOW {
                base termination-state;
                description "A flexible termination that is currently terminated for server to client flow only.";
            }
            identity TERMINATION_STATE_TERMINATED_CLIENT_TO_SERVER_FLOW {
                base termination-state;
                description "A flexible termination that is currently terminated for client to server flow only.";
            }
            identity TERMINATION_STATE_TERMINATED_BIDIRECTIONAL {
                base termination-state;
                description "A flexible termination that is currently terminated in both directions of flow.";
            }
            identity TERMINATION_STATE_LP_PERMENANTLY_TERMINATED {
                base termination-state;
                description "A non-flexible termination that is always terminated (in both directions of flow for a bidirectional case and in the one direction of flow for both unidirectional cases).";
            }
            identity TERMINATION_STATE_TERMINATION_STATE_UNKNOWN {
                base termination-state;
                description "There TerminationState cannot be determined.";
            }
            identity PROTECTION_REASON {
                description "none";
            }
            identity PROTECTION_REASON_WAIT_TO_REVERT {
                base protection-reason;
                description "The resource is selected as control is waiting to restore to a preferred resource.";
            }
            identity PROTECTION_REASON_SIGNAL_DEGRADE {
                base protection-reason;
                description "The resource is selected as the best preferred resource is in signal degrade.";
            }
            identity PROTECTION_REASON_SIGNAL_FAIL {
                base protection-reason;
                description "The resource is selected as the best preferred resource is in signal fail.";
            }
            identity ROUTE_SELECTION_CONTROL {
                description "none";
            }
            identity ROUTE_SELECTION_CONTROL_LOCK_OUT {
                base route-selection-control;
                description "The resource is configured to temporarily not be available for use in the protection scheme(s) it is part of.
                    This overrides all other protection control states including forced.
                    If the item is locked out, then it cannot be used under any circumstances.
                    Note: Only relevant when part of a protection scheme.
                    Note: if a protection process that has a relationship to the item (i.e. is one of the options the protection process may choose) is deactivated by being isFrozen = true) then the lockout request will be rejected. ";
            }
            identity ROUTE_SELECTION_REASON {
                description "none";
            }
            identity SWITCH_CONTROL {
                description "none";
            }
            identity SWITCH_CONTROL_NORMAL {
                base switch-control;
                description "No administrative control applied to the switch.";
            }
            identity SWITCH_CONTROL_MANUAL {
                base switch-control;
                description "Resource temporarily chosen by control configuration where the resource is not the preferred resource.
                    Preferred resource has highest priority.
                    Temporarily overrides reversion.
                    If this resource fails, it will switch to best available resource. 
                    If resource selected is shared and another FC requires the resource, then the selection control will change to Normal and switch to best available based upon normal rules.
                    Cannot manually switch a Forced switch, cannot remove a forced switch, cannot switch to a locked out item and will be rejected if the protection process is deactivated by being Freeze = true).
                    A manual switch/route that is selecting an FcPort, LTP, FC, Link or Route that is subsequently set to LOCK_OUT will have the manual removed (changed to NORMAL) and will switch away from the  FcPort with LOCK_OUT to best available based upon normal rules.
                    A manual switch that is selecting an FcPort that is subsequently selected by a Forced switch will be restored to normal operation and the manual will be removed.
                    A manual switch/route that is selecting an FcPort, LTP, FC, Link or Route that is subsequently manual selected by another switch/route  will have the manual removed and will switch away from the FcPort.
                    Can be returned to NORMAL by configuration action.";
            }
            identity SWITCH_CONTROL_FORCED {
                base switch-control;
                description "Resource temporarily chosen by control configuration where the resource is not the preferred resource.
                    Preferred resource has highest priority.
                    Temporarily overrides reversion.
                    If this resource fails it will NOT switch. 
                    If resource selected is shared and another FC requires the resource through a FORCE on that FC and the FC is of a higher FcPriority then the selection control on this FC will change to NORMAL and switch to best available based upon normal rules.
                    If the resource selected is then set to LOCK_OUT then the selection control will change to NORMAL and switch to best available based upon normal rules.
                    Can be returned to NORMAL by configuration action.";
            }
            identity SWITCH_STATE_REASON {
                description "none";
            }
            identity REVERSION_MODE {
                description "none";
            }
            identity REVERSION_MODE_REVERTIVE {
                base reversion-mode;
                description "An FC switched to a lower priority (non-preferred) resource will revert to a higher priority (preferred) resource when that recovers (potentially after some hold-off time).";
            }
            identity REVERSION_MODE_NON-REVERTIVE {
                base reversion-mode;
                description "An FC switched to a lower priority (non-preferred) resource will not revert to a higher priority (preferred) resource when that recovers.";
            }
            identity RESILIENCE_CONTROL {
                description "none";
            }
            identity RESILIENCE_CONTROL_QUIESCENT {
                base resilience-control;
                description "none";
            }
            identity RESILIENCE_CONTROL_RESTORING {
                base resilience-control;
                description "none";
            }
            identity RESILIENCE_CONTROL_RECOVERY_FAILED {
                base resilience-control;
                description "none";
            }
            identity RESILIENCE_CONTROL_UNKNOWN {
                base resilience-control;
                description "none";
            }
            identity RUN_MODE {
                description "none";
            }
            identity RUN_MODE_FREE_RUN {
                base run-mode;
                description "The ckock is not synchronized to another clock.";
            }
            identity RUN_MODE_LOCKED {
                base run-mode;
                description "The clock is synchronised to another clock.";
            }
            identity RUN_MODE_HOLD_OVER {
                base run-mode;
                description "The clock was previously synchonised to another clock but that timing input has been lost.
                    The clock is set to the last known synchronization.";
            }
            identity OPERATIONAL_STATE {
                description "none";
            }
            identity OPERATIONAL_STATE_DISABLED {
                base operational-state;
                description "The resource is unable to meet the SLA of the user of the resource. 
                    If no (explicit) SLA is defined the resource is disabled if it is totally inoperable and unable to provide service to the user.";
            }
            identity OPERATIONAL_STATE_ENABLED {
                base operational-state;
                description "The resource is partially or fully operable and available for use.";
            }
            identity ADMINISTRATIVE_STATE {
                description "none";
            }
            identity ADMINISTRATIVE_STATE_LOCKED {
                base administrative-state;
                description "Users are administratively prohibited from making use of the resource.";
            }
            identity ADMINISTRATIVE_STATE_UNLOCKED {
                base administrative-state;
                description "Users are allowed to use the resource.";
            }
            identity ADMINISTRATIVE_STATE_SHUTTING_DOWN {
                base administrative-state;
                description "The entity is administratively restricted to existing instances of use only. There may be specific actions to remove existing uses. No new instances of use can be enabled.
                    The resource automatically transitions to “locked” when the last user quits. 
                    The administrative state is not visible in the client context. 
                    The lifecycle state “pending removal” should be used to indicate to the client that the provider intends to remove the resource.";
            }
            identity ADMINISTRATIVE_CONTROL {
                description "none";
            }
            identity ADMINISTRATIVE_CONTROL_UNLOCK {
                base administrative-control;
                description "The intention is for the entity to become unlocked.
                    The entity may already be UNLOCKED.";
            }
            identity ADMINISTRATIVE_CONTROL_LOCK_PASSIVE {
                base administrative-control;
                description "The intention is for the entity to become locked but no effort is expected to move to the Locked state (the state will be achieved once all users stop using the resource). 
                    The entity may be LOCKED.";
            }
            identity ADMINISTRATIVE_CONTROL_LOCK_ACTIVE {
                base administrative-control;
                description "The intention is for the entity to become locked and it is expected that effort will be made to move to the Locked state (users will be actively removed). 
                    The entity may already be LOCKED.";
            }
            identity ADMINISTRATIVE_CONTROL_LOCK_IMMEDIATE {
                base administrative-control;
                description "The intention is for the entity to become locked and it is expected to move to the Locked state immediately (users will be force removed). 
                    The entity may already be LOCKED.";
            }
            identity ADMINISTRATIVE_CONTROL_QUIESCENT {
                base administrative-control;
                description "The administrative state is at a stable value (LOCKED/UNLOCKED) and no action is being taken.";
            }
            identity LIFECYCLE_STATE {
                description "none";
            }
            identity LIFECYCLE_STATE_PLANNED {
                base lifecycle-state;
                description "The resource is planned but is not present in the network.
                    Should include a 'time' when the resources are expected to be installed.";
            }
            identity LIFECYCLE_STATE_POTENTIAL_AVAILABLE {
                base lifecycle-state;
                description "The supporting resources are present in the network but are shared with other clients; or require further configuration before they can be used; or both.
                    (1) When a potential resource is configured and allocated to a client it is moved to the INSTALLED state for that client.
                    (2) If the potential resource has been consumed (e.g. allocated to another client) it is moved to the POTENTIAL BUSY state for all other clients.";
            }
            identity LIFECYCLE_STATE_POTENTIAL_BUSY {
                base lifecycle-state;
                description "The supporting resources are present in the network but have been allocated to other clients.";
            }
            identity LIFECYCLE_STATE_INSTALLED {
                base lifecycle-state;
                description "The resource is present in the network and is capable of providing the service.";
            }
            identity LIFECYCLE_STATE_PENDING_REMOVAL {
                base lifecycle-state;
                description "The resource has been marked for removal.  Should include a “time” when the resources are expected to be removed.";
            }
            identity BLOCK_DIRECTION {
                description "none";
            }
            identity BLOCK_DIRECTION_NO_BLOCK {
                base block-direction;
                description "none";
            }
            identity ACTION_VERBS {
                description "none";
            }
            identity ACTION_VERBS_CREATE_POST_ADD {
                base action-verbs;
                description "none";
            }
            identity ACTION_VERBS_SET_UPDATE_PUT_MODIFY_WRITE_ADD {
                base action-verbs;
                description "none";
            }
            identity ACTION_VERBS_GET_READ {
                base action-verbs;
                description "none";
            }
            identity ACTION_VERBS_DELETE_REMOVE {
                base action-verbs;
                description "none";
            }
            identity ACTIVITY_DIRECTIVE {
                description "none";
            }
            identity ACTIVITY_DIRECTIVE_STRUCTURE_IS_NOT {
                base activity-directive;
                description "none";
            }
            identity ACTIVITY_DIRECTIVE_NEW_STRUCTURE_AND_VALUES {
                base activity-directive;
                description "none";
            }
            identity ACTIVITY_DIRECTIVE_INCREMENTAL_STRUCTURE_AND_VALUES {
                base activity-directive;
                description "none";
            }
            identity ACTIVITY_DIRECTIVE_ONLY_VALUES_IN_EXISTING_STRUCTURE {
                base activity-directive;
                description "none";
            }
            identity ACTIVITY_DIRECTIVE_DEFINED_BY_VERB {
                base activity-directive;
                description "none";
            }
            identity ACTION_EFFORT {
                description "none";
            }
            identity ACTION_EFFORT_BEST_EFFORT {
                base action-effort;
                description "none";
            }
            identity ACTION_EFFORT_EXACT_MATCH {
                base action-effort;
                description "none";
            }
            identity PAUSE_RESUME_RULE {
                description "none";
            }
            identity PAUSE_RESUME_RULE_NO_PAUSE_POSSIBLE {
                base pause-resume-rule;
                description "none";
            }
            identity CONNECTOR_AND_PIN_ORIENTATION {
                description "none";
            }
            identity CONNECTOR_AND_PIN_ORIENTATION_MALE {
                base connector-and-pin-orientation;
                description "The connecting elements are dominantly protrusions.";
            }
            identity CONNECTOR_AND_PIN_ORIENTATION_FEMALE {
                base connector-and-pin-orientation;
                description "The connecting elements are dominantly indentations.";
            }
            identity CONNECTOR_AND_PIN_ORIENTATION_SYMMETRIC_NEUTRAL {
                base connector-and-pin-orientation;
                description "The pin (and housing) orientation combination is such that it is symmetric so a connector is compatible with itself.
                    The connecting element may be a surface rather than protrusions or indentations.";
            }
            identity EQUIPMENT_CATEGORY {
                description "none";
            }
            identity EQUIPMENT_CATEGORY_SUBRACK {
                base equipment-category;
                description "An assembly with holders designed to accommodate CIRCUIT_PACKs. 
                    The assembly is designed to be mounted in a RACK.";
            }
            identity EQUIPMENT_CATEGORY_CIRCUIT_PACK {
                base equipment-category;
                description "An assembly with connectors compatible with those in a holder.
                    The assembly is designed to be mounted in a holder (SLOT) of a SUBRACK.
                    May also support holders (SLOTs) for SMALL_FORMFACTOR_PLUGGABLEs.";
            }
            identity EQUIPMENT_CATEGORY_SMALL_FORMFACTOR_PLUGGABLE {
                base equipment-category;
                description "A small assembly (compared to a CIRCUIT_PACK) with connectors compatible with those in a holder.
                    The assembly is designed to be mounted in a holder (SLOT) of a CIRCUIT_PACK or STAND_ALONE_UNIT.";
            }
            identity EQUIPMENT_CATEGORY_STAND_ALONE_UNIT {
                base equipment-category;
                description "An assembly with connectors for cabling and potentially with holders.
                    The assembly is designed to be mounted in a freeform environment (on a table or simple mechanical cabinet).
                    May support holders (SLOTs) for CIRCUIT_PACKs or for SMALL_FORMFACTOR_PLUGGABLEs.";
            }
            identity EQUIPMENT_CATEGORY_RACK {
                base equipment-category;
                description "A mechanical assembly with cabling and predefined mounting points for particular SUBRACK types.
                    The assembly is designed to be mounted on the floor in a row with other RACKs.";
            }
            identity HOLDER_CATEGORY {
                description "none";
            }
            identity HOLDER_CATEGORY_SLOT {
                base holder-category;
                description "A guided holder with fixed connectors.
                    The guided holder is designed to take a particular form of CIRCUIT_PACK or SMALL_FORMFACTOR_PLUGGABLE";
            }
            identity FORWARDING_RULE {
                description "none";
            }
            identity FORWARDING_RULE_CANNOT_FORWARD_ACROSS_FD_LINK {
                base forwarding-rule;
                description "LTPs referenced by the FD (or indirectly by the Link between FDs) cannot have FCs created between them.
                    This rule overrides all others.";
            }
            identity FORWARDING_RULE_MUST_FORWARD_ACROSS_FD_LINK {
                base forwarding-rule;
                description "LTPs referenced by the FD (or indirectly by the Link between FDs) MUST have FCs created between them.
                    This rule overrides all others except the CANNOT_FORWARD rule.";
            }
            identity FORWARDING_RULE_MAY_FORWARD_ACROSS_FD_LINK {
                base forwarding-rule;
                description "LTPs referenced by the FD (or indirectly by the Link between FDs) may have FCs created between them.
                    FCs may not be created between points that are not related by this rule either directly in an FD or indirectly via a Link linking two or more FDs.
                    For a Link points in an FD at one end of the Link can be connected to points in an FD at an other end of the Link.";
            }
            identity FORWARDING_RULE_NULL_FORWARDING_RULE {
                base forwarding-rule;
                description "none";
            }
            identity RULE_TYPE {
                description "none";
            }
            identity RULE_TYPE_FORWARDING {
                base rule-type;
                description "The rule relates to creation of FCs.";
            }
            identity RULE_TYPE_COST {
                base rule-type;
                description "The rule relates to forwarding cost.";
            }
            identity RULE_TYPE_RISK {
                base rule-type;
                description "The rule relates to forwarding risk.";
            }
            identity RULE_TYPE_CAPACITY {
                base rule-type;
                description "none";
            }
            identity PORT_ROLE_RULE {
                description "none";
            }
            identity PORT_ROLE_RULE_SAME_ROLE {
                base port-role-rule;
                description "none";
            }
            identity PORT_ROLE_RULE_DIFFERENT_ROLE {
                base port-role-rule;
                description "none";
            }
            identity PORT_ROLE_RULE_ANY_ROLE {
                base port-role-rule;
                description "none";
            }
            identity SIGNAL_PROPERTY_VALUE_RULE {
                description "none";
            }
            identity SIGNAL_PROPERTY_VALUE_RULE_SAME_VALUE {
                base signal-property-value-rule;
                description "none";
            }
            identity SIGNAL_PROPERTY_VALUE_RULE_ANY_VALUE {
                base signal-property-value-rule;
                description "none";
            }
            identity TERMINATION_DIRECTION {
                description "none";
            }
            identity TERMINATION_DIRECTION_BIDIRECTIONAL {
                base termination-direction;
                description "A Termination with both SINK and SOURCE flows.";
            }
            identity TERMINATION_DIRECTION_SINK {
                base termination-direction;
                description "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity.";
            }
            identity TERMINATION_DIRECTION_SOURCE {
                base termination-direction;
                description "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity.";
            }
            identity TERMINATION_DIRECTION_UNDEFINED_OR_UNKNOWN {
                base termination-direction;
                description "Not a normal state. The system is unable to determine the correct value.";
            }
            identity TERMINATION_DIRECTION {
                description "none";
            }
            identity TERMINATION_DIRECTION_BIDIRECTIONAL {
                base termination-direction;
                description "A Termination with both SINK and SOURCE flows.";
            }
            identity TERMINATION_DIRECTION_SINK {
                base termination-direction;
                description "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base termination-direction;
                description "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base termination-direction;
                description "Not a normal state. The system is unable to determine the correct value.";
            }
            identity ACTION_VERBS {
                description "none";
            }
            identity ACTION_VERBS_CREATE_POST_ADD {
                base action-verbs;
                description "none";
            }
            identity ACTION_VERBS_SET_UPDATE_PUT_MODIFY_WRITE_ADD {
                base action-verbs;
                description "none";
            }
            identity ACTION_VERBS_GET_READ {
                base action-verbs;
                description "none";
            }
            identity ACTION_VERBS_DELETE_REMOVE {
                base action-verbs;
                description "none";
            }
            identity DIRECTION {
                description "none";
            }
            identity DIRECTION_IN {
                base direction;
                description "none";
            }
            identity DIRECTION_OUT {
                base direction;
                description "none";
            }
            identity DIRECTION_BIDIRECTIONAL {
                base direction;
                description "none";
            }
            /***********************
            * package topology
            **********************/ 
                grouping cost-characteristics {
                    leaf cost-name {
                        type string;
                        description "The cost characteristic will related to some aspect of the ForwardingEntity (e.g. $ cost, routing weight). This aspect will be conveyed by the costName.";
                    }
                    leaf cost-value {
                        type string;
                        description "The specific cost.";
                    }
                    leaf cost-algorithm {
                        type to-be-defined;
                        description "The cost may vary based upon some properties of the ForwardingEntity. The rules for the variation are conveyed by the costAlgorithm.";
                    }
                    description "The information for a particular cost characteristic.";
                }
                grouping risk-characteristic {
                    leaf risk-characteristic-name {
                        type string;
                        description "The name of the risk characteristic. The characteristic may be related to a specific degree of closeness. 
                            For example, a particular characteristic may apply to failures that are localized (e.g. to one side of a road) where as another characteristic may relate to failures that have a broader impact (e.g. both sides of a road that crosses a bridge).
                            Depending upon the importance of the traffic being routed different risk characteristics will be evaluated.";
                    }
                    leaf-list risk-identifier {
                        type string;
                        min-elements 1;
                        description "A list of the identifiers of each physical/geographic unit (with the specific risk characteristic) that is related to a segment of the ForwardingEntity.";
                    }
                    description "The information for a particular risk characteristic where there is a list of risk identifiers related to that characteristic.";
                }
                grouping capacity {
                    leaf total-size {
                        type string;
                        description "Total capacity of the ForwardingEntity in Mbits/s";
                    }
                    leaf number-of-client-instances {
                        type string;
                        description "Where there is some limit to the number of client (e.g. in a channelized case).";
                    }
                    leaf maximum-client-size {
                        type string;
                        description "Where a client is of variable capacity but due to some underlying realization the maximum size of the client is smaller than the totalSize.";
                    }
                    leaf numbering-range {
                        type string;
                        description "Method for identifying units of capacity via some numbering scheme.";
                    }
                    description "Information on capacity of a particular ForwardingEntity.";
                }
                grouping validation-mechanism {
                    leaf validation-mechanism {
                        type string;
                        description "Name of mechanism used to validate adjacency.";
                    }
                    leaf layer-protocol-adjacency-validated {
                        type string;
                        description "State of validation.";
                    }
                    leaf validation-robustness {
                        type string;
                        description "Quality of validation (i.e. how likely is the stated validation to be invalid).";
                    }
                    description "Identifies the validation mechanism and describes the characteristics of that mechanism.";
                }
                grouping queuing-latency {
                    leaf traffic-property {
                        type string;
                        description "The identifier of the specific traffic property to which the queuing latency applies.";
                    }
                    leaf latency-for-traffic-with-property {
                        type string;
                        description "The specific queuing latency for the traffic property.";
                    }
                    description "Provides information on latency characteristic for a particular stated trafficProperty.";
                }

            /***********************
            * package resilience
            **********************/ 
                typedef ProtectionReason {
                    type identityref {
                        base protection-reason;
                    }
                    description "The cause of the current protection state.";
                }
                typedef RouteSelectionControl {
                    type identityref {
                        base switch-control;
                        base route-selection-control;
                    }
                    description "Possible degrees of administrative control applied to the Route selection.";
                }
                typedef RouteSelectionReason {
                    type identityref {
                        base protection-reason;
                        base switch-control;
                        base route-selection-control;
                        base route-selection-reason;
                    }
                    description "The cause of the current route selection.";
                }
                typedef SwitchControl {
                    type identityref {
                        base switch-control;
                    }
                    description "none";
                }
                typedef SwitchStateReason {
                    type identityref {
                        base protection-reason;
                        base switch-control;
                        base switch-state-reason;
                    }
                    description "Explains the reason for the current switch state.";
                }
                typedef ReversionMode {
                    type identityref {
                        base reversion-mode;
                    }
                    description "The reversion mode associated with protection.";
                }
                grouping global-pac {
                    uses global-class;
                    description "Provides the properties of a GlobalClass via composition.";
                }
                grouping local-pac {
                    uses local-class;
                    description "Provides the properties of a LocalClass via composition.";
                }
                typedef ProtectionType {
                    type string;
                    description "Identifies the type of protection of an FcSwitch.";
                }
                typedef ResilienceControl {
                    type identityref {
                        base resilience-control;
                    }
                    description "none";
                }

            /***********************
            * package timing
            **********************/ 
                typedef RunMode {
                    type identityref {
                        base run-mode;
                    }
                    description "none";
                }

            typedef layer-protocol-name {
                type string;
                description "Provides a controlled list of layer protocol names and indicates the naming authority.
                    Note that it is expected that attributes will be added to this structure to convey the naming authority name, the name of the layer protocol using a human readable string and any particular standard reference.
                    Layer protocol names include:
                    -    Layer 1 (L1): OTU, ODU
                    -    Layer 2 (L2): Carrier Grade Ethernet (ETY, ETH), MPLS-TP (MT)
                    ";
            }
            typedef port-role {
                type string;
                description "The role of a port in the context of the function of the forwarding entity that it bounds.";
            }
            typedef port-direction {
                type identityref {
                    base port-direction;
                }
                description "The orientation of flow at the Port of a Forwarding entity.";
            }
            typedef forwarding-direction {
                type identityref {
                    base forwarding-direction;
                }
                description "The directionality of a Forwarding entity.";
            }
            typedef termination-direction {
                type identityref {
                    base termination-direction;
                }
                description "The directionality of a termination entity.";
            }
            typedef extended-termination-direction {
                type identityref {
                    base termination-direction;
                    base extended-termination-direction;
                }
                description "Extended to include contra-direction considerations. Only applies to LP and elements of LP not to LTP.";
            }
            typedef termination-state {
                type identityref {
                    base termination-state;
                }
                description "Provides support for the range of behaviors and specific states that an LP can take with respect to termination of the signal.
                    Indicates to what degree the LayerTermination is terminated.";
            }

        /***********************
        * package object-classes
        **********************/ 
            /***********************
            * package topology
            **********************/ 
                grouping transfer-cost-pac {
                    list cost-characteristic {
                        min-elements 1;
                        uses cost-characteristics;
                        description "The list of costs where each cost relates to some aspect of the ForwardingEntity.";
                    }
                    description "The cost characteristics of a ForwardingEntity not necessarily correlated to the cost of the underlying physical realization. 
                        They may be quite specific to the individual ForwardingEntity (e.g. opportunity cost) and relates to layer capacity
                        There may be many perspectives from which cost may be considered for a particular ForwardingEntity and hence many specific costs and potentially cost algorithms. 
                        Using an entity will incur a cost. ";
                }
                grouping risk-parameter-pac {
                    list risk-characteristic {
                        min-elements 1;
                        uses risk-characteristic;
                        description "A list of risk characteristics for consideration in an analysis of shared risk. Each element of the list represents a specific risk consideration.";
                    }
                    description "The risk characteristics of a ForwardingEntity come directly from the underlying physical realization. 
                        The risk characteristics propagate from the physical realization to the client and from the server layer to the client layer; this propagation may be modified by protection.
                        A ForwardingEntity may suffer degradation or failure as a result of a problem in a part of the underlying realization.
                        The realization can be partitioned into segments which have some relevant common failure modes.
                        There is a risk of failure/degradation of each segment of the underlying realization.
                        Each segment is a part of a larger physical/geographical unit that behaves as one with respect to failure (i.e. a failure will have a high probability of impacting the whole unit (e.g. all cables in the same duct).
                        Disruptions to that larger physical/geographical unit will impact (cause failure/errors to) all ForwardingEntities that use any part of that larger physical/geographical entity.
                        Any ForwardingEntity that uses any part of that larger physical/geographical unit will suffer impact and hence each ForwardingEntity shares risk.
                        The identifier of each physical/geographical unit that is involved in the realization of each segment of a ForwardingEntity can be listed in the RiskParameter_Pac of that ForwardingEntity.
                        A segment has one or more risk characteristic.
                        Shared risk between two ForwardingEntities compromises the integrity of any solution that use one of those ForwardingEntity as a backup for the other.
                        Where two ForwardingEntities have a common risk characteristic they have an elevated probability of failing simultaneously compared to two ForwardingEntities that do not share risk characteristics.";
                }
                grouping layer-protocol-transition-pac {
                    leaf-list transitioned-layer-protocol {
                        type string;
                        min-elements 2;
                        description "Provides the ordered structure of layer protocol transitions encapsulated in the ForwardingEntity. 
                            The list starts with the client side as the first entry and includes all layer-protocol names (hence the smallest number is 2 as otherwise the Link is not transitional). 
                            The ordering relates also to the LinkPort role (which emphasizes the orientation). 
                            Where the transitional link is multi-ported and layer asymmetric the list includes the superset of layer-protocol names. 
                            Transitional links can only be applied where the transition for each port is such that all transitions between any ports are subsequences of the list. 
                            The specific subsequence is determined by the LayerProtocols of the LTP associated with the LinkPort and the role of the LinkPort.";
                    }
                    leaf-list ltp {
                        type leafref {
                            path '/core-model:network-control-domain/core-model:network-element/core-model:ltp/core-model:';
                        }
                        min-elements 1;
                        description "Lists the LTPs that define the layer protocol transition of the transitional link.";
                    }
                    description "The transition characteristics are relevant for a Link that is formed by abstracting one or more LTPs (in a stack) to focus on the flow and deemphasize the protocol transformation. 
                        This abstraction is relevant when considering multi-layer routing. 
                        The layer protocols of the LTP and the order of their application to the signal is still relevant and needs to be accounted for (this is derived from the LTP spec details).
                        This Pac provides the relevant abstractions of the LTPs and provides the necessary association to the LTPs involved.
                        Links that include details in this Pac are often referred to as Transitional Links.";
                }
                grouping transfer-timing-pac {
                    leaf fixed-latency-characteristic {
                        type string;
                        description "A ForwardingEntity suffers delay caused by the realization of the servers (e.g. distance related; FEC encoding etc.) along with some client specific processing. This is the total average latency effect of the ForwardingEntity.";
                    }
                    leaf jitter-characteristic {
                        if-feature present-if-jittercharacteristic-information-is-relevant-to-usage-and-statement-can-be-made-that-applies-equally-to-all-flows-that-can-be-supported-by-the-forwardingentity
note-that-if-jittercharacteristic-is-relevant-but-consistent-statement-cannot-be-made-then-the-forwardingentity-should-be-described-in-terms-of-subordinate-parts-against-which-coherent-statements-can-be-made
note-that-this-only-applies-to-tdm;
                        type string;
                        description "High frequency deviation from true periodicity of a signal and therefore a small high rate of change of transfer latency.
                            Applies to TDM systems (and not packet).";
                    }
                    leaf wander-characteristic {
                        if-feature present-if-wandercharacteristic-information-is-relevant-to-usage-and-statement-can-be-made-that-applies-equally-to-all-flows-that-can-be-supported-by-the-forwardingentity
note-that-if-wandercharacteristic-is-relevant-but-consistent-statement-cannot-be-made-then-the-forwardingentity-should-be-described-in-terms-of-subordinate-parts-against-which-coherent-statements-can-be-made
note-that-this-only-applies-to-tdm;
                        type string;
                        description "Low frequency deviation from true periodicity of a signal and therefore a small low rate of change of transfer latency.
                            Applies to TDM systems (and not packet).";
                    }
                    list queuing-latency-characteristic {
                        if-feature present-if-queuinglatencycharacteristic-information-is-relevant-to-usage-and-statement-can-be-made-that-applies-equally-to-all-flows-that-can-be-supported-by-the-forwardingentity
there-may-be-more-than-one-instance-if-the-queuing-behavior-depends-upon-traffic-properties
note-that-if-queuinglatencycharacteristic-is-relevant-but-consistent-statement-cannot-be-made-then-the-forwardingentity-should-be-described-in-terms-of-subordinate-parts-against-which-coherent-statements-can-be-made
note-that-this-only-applies-to-packet-system;
                        uses queuing-latency;
                        description "The effect on the latency of a queuing process. This only has significant effect for packet based systems and has a complex characteristic.";
                    }
                    description "A ForwardingEntity will suffer effects from the underlying physical realization related to the timing of the information passed by the ForwardingEntity.";
                }
                grouping transfer-integrity-pac {
                    leaf error-characteristic {
                        if-feature present-if-errorcharacteristic-information-is-relevant-to-usage-and-statement-can-be-made-that-applies-equally-to-all-flows-that-can-be-supported-by-the-forwardingentity
note-that-if-errorcharacteristic-is-relevant-but-consistent-statement-cannot-be-made-then-the-forwardingentity-should-be-described-in-terms-of-subordinate-parts-against-which-coherent-statements-can-be-made
note-that-this-only-applies-to-tdm;
                        type string;
                        description "Describes the degree to which the signal propagated can be errored. 
                            Applies to TDM systems as the errored signal will be propagated and not packet as errored packets will be discarded.";
                    }
                    leaf loss-characteristic {
                        if-feature present-if-losscharacteristic-information-is-relevant-to-usage-and-statement-can-be-made-that-applies-equally-to-all-flows-that-can-be-supported-by-the-forwardingentity
note-that-if-losscharacteristic-is-relevant-but-consistent-statement-cannot-be-made-then-the-forwardingentity-should-be-described-in-terms-of-subordinate-parts-against-which-coherent-statements-can-be-made
note-that-this-only-applies-to-packet-systems;
                        type string;
                        description "Describes the acceptable characteristic of lost packets where loss may result from discard due to errors or overflow.
                            Applies to packet systems and not TDM (as for TDM errored signals are propagated unless grossly errored and overflow/underflow turns into timing slips).";
                    }
                    leaf repeat-delivery-characteristic {
                        if-feature present-if-repeatdeliverycharacteristic-information-is-relevant-to-usage-and-statement-can-be-made-that-applies-equally-to-all-flows-that-can-be-supported-by-the-forwardingentity
note-that-if-repeatdeliverycharacteristic-is-relevant-but-consistent-statement-cannot-be-made-then-the-forwardingentity-should-be-described-in-terms-of-subordinate-parts-against-which-coherent-statements-can-be-made
note-that-this-primarily-applies-to-packet-systems-where-a-packet-may-be-delivered-more-than-once-(in-fault-recovery-for-example)-
note-that-it-can-also-apply-to-tdm-where-several-frames-may--be-received-twice-due-to-switching-in-a-system-with-a-large-differential-propagation-delay;
                        type string;
                        description "Primarily applies to packet systems where a packet may be delivered more than once (in fault recovery for example). 
                            It can also apply to TDM where several frames may be received twice due to switching in a system with a large differential propagation delay.";
                    }
                    leaf delivery-order-characteristic {
                        if-feature present-if-deliveryordercharacteristic-information-is-relevant-to-usage-and-statement-can-be-made-that-applies-equally-to-all-flows-that-can-be-supported-by-the-forwardingentity
note-that-if-deliveryordercharacteristic-is-relevant-but-consistent-statement-cannot-be-made-then-the-forwardingentity-should-be-described-in-terms-of-subordinate-parts-against-which-coherent-statements-can-be-made
note-that-this-only-applies-to-packet-systems
;
                        type string;
                        description "Describes the degree to which packets will be delivered out of sequence.
                            Does not apply to TDM as the TDM protocols maintain strict order.";
                    }
                    leaf unavailable-time-characteristic {
                        type string;
                        description "Describes the duration for which there may be no valid signal propagated.";
                    }
                    leaf server-integrity-process-characteristic {
                        if-feature present-if-serverintegrityprocesscharacteristic-information-is-relevant-to-usage-and-statement-can-be-made-that-applies-equally-to-all-flows-that-can-be-supported-by-the-forwardingentity
note-that-if-serverintegrityprocesscharacteristic-is-relevant-but-consistent-statement-cannot-be-made-then-the-forwardingentity-should-be-described-in-terms-of-subordinate-parts-against-which-coherent-statements-can-be-made
note-that-this-only-applies-where-the-server-has-some-error-recovery-mechanism-alters-the-characteristics-of-the-link-from-a-normal-distribution;
                        type string;
                        description "Describes the effect of any server integrity enhancement process on the characteristics of the ForwardingEntity.";
                    }
                    description "Transfer integrity characteristic covers expected/specified/acceptable characteristic of degradation of the transferred signal.
                        It includes all aspects of possible degradation of signal content as well as any damage of any form to the total ForwardingEntity and to the carried signals.
                        Note that the statement is of total impact to the ForwardingEntity so any partial usage of the ForwardingEntity (e.g. a signal that does not use full capacity) will only suffer its portion of the impact.";
                }
                grouping transfer-capacity-pac {
                    container total-potential-capacity {
                        uses capacity;
                        description "An optimistic view of the capacity of the ForwardingEntity assuming that any shared capacity is available to be taken.";
                    }
                    container available-capacity {
                        uses capacity;
                        description "Capacity available to be assigned.";
                    }
                    list capacity-assigned-to-user-view {
                        uses capacity;
                        description "Capacity already assigned.";
                    }
                    leaf capacity-interaction-algorithm {
                        type string;
                        description "A reference to an algorithm that describes how various chunks of allocated capacity interact (e.g. when shared).";
                    }
                    description "The ForwardingEntity derives capacity from the underlying realization. 
                        A ForwardingEntity may be an abstraction and virtualization of a subset of the underlying capability offered in a view or may be directly reflecting the underlying realization.
                        A ForwardingEntity may be directly used in the view or may be assigned to another view for use.
                        The clients supported by a multi-layer ForwardingEntity may interact such that the resources used by one client may impact those available to another. This is derived from the LTP spec details.
                        Represents the capacity available to user (client) along with client interaction and usage. 
                        A ForwardingEntity may reflect one or more client protocols and one or more members for each profile.";
                }
                grouping forwarding-entity {
                    container risk-parameter-pac {
                        if-feature present-if-risk-information-is-relevant-to-usage-and-statement-can-be-made-that-applies-equally-to-all-flows-that-can-be-supported-by-the-forwardingentity
note-that-if-risk-is-relevant-but-consistent-statement-cannot-be-made-then-the-forwardingentity-should-be-described-in-terms-of-subordinate-parts-against-which-coherent-statements-can-be-made;
                        uses risk-parameter-pac;
                        description "none";
                    }
                    container transfer-cost-pac {
                        if-feature present-if-cost-information-is-relevant-to-usage-and-statement-can-be-made-that-applies-equally-to-all-flows-that-can-be-supported-by-the-forwardingentity
note-that-if-cost-is-relevant-but-consistent-statement-cannot-be-made-then-the-forwardingentity-should-be-described-in-terms-of-subordinate-parts-against-which-coherent-statements-can-be-made;
                        uses transfer-cost-pac;
                        description "none";
                    }
                    container transfer-timing-pac {
                        if-feature present-if-transfer-timing-information-is-relevant-to-usage-and-statement-can-be-made-that-applies-equally-to-all-flows-that-can-be-supported-by-the-forwardingentity
note-that-if-transfer-timing-is-relevant-but-consistent-statement-cannot-be-made-then-the-forwardingentity-should-be-described-in-terms-of-subordinate-parts-against-which-coherent-statements-can-be-made;
                        uses transfer-timing-pac;
                        description "none";
                    }
                    container transfer-capacity-pac {
                        if-feature present-if-transfer-capacity-information-is-relevant-to-usage-and-statement-can-be-made-that-applies-equally-to-all-flows-that-can-be-supported-by-the-forwardingentity
note-that-if-transfer-capacity-is-relevant-but-consistent-statement-cannot-be-made-then-the-forwardingentity-should-be-described-in-terms-of-subordinate-parts-against-which-coherent-statements-can-be-made;
                        uses transfer-capacity-pac;
                        description "none";
                    }
                    container transfer-integrity-pac {
                        if-feature present-if-transfer-integrity-information-is-relevant-to-usage-and-statement-can-be-made-that-applies-equally-to-all-flows-that-can-be-supported-by-the-forwardingentity
note-that-if-transfer-integrity-is-relevant-but-consistent-statement-cannot-be-made-then-the-forwardingentity-should-be-described-in-terms-of-subordinate-parts-against-which-coherent-statements-can-be-made;
                        uses transfer-integrity-pac;
                        description "none";
                    }
                    container validation-pac {
                        if-feature present-if-validation-information-is-relevant-to-usage-and-statement-can-be-made-that-applies-equally-to-all-flows-that-can-be-supported-by-the-forwardingentity
note-that-if-validation-is-relevant-but-consistent-statement-cannot-be-made-then-the-forwardingentity-should-be-described-in-terms-of-subordinate-parts-against-which-coherent-statements-can-be-made
note-that-validation-may-not-be-possible-for-the-specific-layer-protocol-or-in-the-particular-case;
                        uses validation-pac;
                        description "none";
                    }
                    list layer-transition-pac {
                        if-feature present-if-layer-transition-information-is-relevant-to-usage-and-statement-can-be-made-that-applies-equally-to-all-flows-that-can-be-supported-by-the-forwardingentity
note-that-if-layer-transition-is-relevant-but-consistent-statement-cannot-be-made-then-the-forwardingentity-should-be-described-in-terms-of-subordinate-parts-against-which-coherent-statements-can-be-made
note-that-layer-transition-occurs-in-a-limited-number-of-cases;
                        uses layer-protocol-transition-pac;
                        description "none";
                    }
                    description "A ForwardingEntity is an abstract representation of the emergent effect of the combined functioning of an arrangement of components (running hardware, software running on hardware etc.). 
                        The effect can be considered as the realization of the potential for apparent communication adjacency for entities that are bound to the terminations at the boundary of the ForwardingEntity.
                        The ForwardingEntity enables the creation of constrained forwarding to achieve the apparent adjacency.
                        The apparent adjacency has intended performance degraded from perfect adjacency and a statement of that degradation is conveyed via the attributes of the packages associated with this class.";
                }
                grouping validation-pac {
                    list validation-mechanism {
                        min-elements 1;
                        uses validation-mechanism;
                        description "Provides details of the specific validation mechanism(s) used to confirm the presence of an intended ForwardingEntity.";
                    }
                    description "Validation covers the various adjacency discovery and reachability verification protocols. Also may cover Information source and degree of integrity.";
                }
                feature present-if-jittercharacteristic-information-is-relevant-to-usage-and-statement-can-be-made-that-applies-equally-to-all-flows-that-can-be-supported-by-the-forwardingentity
note-that-if-jittercharacteristic-is-relevant-but-consistent-statement-cannot-be-made-then-the-forwardingentity-should-be-described-in-terms-of-subordinate-parts-against-which-coherent-statements-can-be-made
note-that-this-only-applies-to-tdm {
                    description "none";
                }
                feature present-if-wandercharacteristic-information-is-relevant-to-usage-and-statement-can-be-made-that-applies-equally-to-all-flows-that-can-be-supported-by-the-forwardingentity
note-that-if-wandercharacteristic-is-relevant-but-consistent-statement-cannot-be-made-then-the-forwardingentity-should-be-described-in-terms-of-subordinate-parts-against-which-coherent-statements-can-be-made
note-that-this-only-applies-to-tdm {
                    description "none";
                }
                feature present-if-queuinglatencycharacteristic-information-is-relevant-to-usage-and-statement-can-be-made-that-applies-equally-to-all-flows-that-can-be-supported-by-the-forwardingentity
there-may-be-more-than-one-instance-if-the-queuing-behavior-depends-upon-traffic-properties
note-that-if-queuinglatencycharacteristic-is-relevant-but-consistent-statement-cannot-be-made-then-the-forwardingentity-should-be-described-in-terms-of-subordinate-parts-against-which-coherent-statements-can-be-made
note-that-this-only-applies-to-packet-system {
                    description "none";
                }
                feature present-if-errorcharacteristic-information-is-relevant-to-usage-and-statement-can-be-made-that-applies-equally-to-all-flows-that-can-be-supported-by-the-forwardingentity
note-that-if-errorcharacteristic-is-relevant-but-consistent-statement-cannot-be-made-then-the-forwardingentity-should-be-described-in-terms-of-subordinate-parts-against-which-coherent-statements-can-be-made
note-that-this-only-applies-to-tdm {
                    description "none";
                }
                feature present-if-losscharacteristic-information-is-relevant-to-usage-and-statement-can-be-made-that-applies-equally-to-all-flows-that-can-be-supported-by-the-forwardingentity
note-that-if-losscharacteristic-is-relevant-but-consistent-statement-cannot-be-made-then-the-forwardingentity-should-be-described-in-terms-of-subordinate-parts-against-which-coherent-statements-can-be-made
note-that-this-only-applies-to-packet-systems {
                    description "none";
                }
                feature present-if-repeatdeliverycharacteristic-information-is-relevant-to-usage-and-statement-can-be-made-that-applies-equally-to-all-flows-that-can-be-supported-by-the-forwardingentity
note-that-if-repeatdeliverycharacteristic-is-relevant-but-consistent-statement-cannot-be-made-then-the-forwardingentity-should-be-described-in-terms-of-subordinate-parts-against-which-coherent-statements-can-be-made
note-that-this-primarily-applies-to-packet-systems-where-a-packet-may-be-delivered-more-than-once-(in-fault-recovery-for-example)-
note-that-it-can-also-apply-to-tdm-where-several-frames-may--be-received-twice-due-to-switching-in-a-system-with-a-large-differential-propagation-delay {
                    description "none";
                }
                feature present-if-deliveryordercharacteristic-information-is-relevant-to-usage-and-statement-can-be-made-that-applies-equally-to-all-flows-that-can-be-supported-by-the-forwardingentity
note-that-if-deliveryordercharacteristic-is-relevant-but-consistent-statement-cannot-be-made-then-the-forwardingentity-should-be-described-in-terms-of-subordinate-parts-against-which-coherent-statements-can-be-made
note-that-this-only-applies-to-packet-systems
 {
                    description "none";
                }
                feature present-if-serverintegrityprocesscharacteristic-information-is-relevant-to-usage-and-statement-can-be-made-that-applies-equally-to-all-flows-that-can-be-supported-by-the-forwardingentity
note-that-if-serverintegrityprocesscharacteristic-is-relevant-but-consistent-statement-cannot-be-made-then-the-forwardingentity-should-be-described-in-terms-of-subordinate-parts-against-which-coherent-statements-can-be-made
note-that-this-only-applies-where-the-server-has-some-error-recovery-mechanism-alters-the-characteristics-of-the-link-from-a-normal-distribution {
                    description "none";
                }
                feature present-if-risk-information-is-relevant-to-usage-and-statement-can-be-made-that-applies-equally-to-all-flows-that-can-be-supported-by-the-forwardingentity
note-that-if-risk-is-relevant-but-consistent-statement-cannot-be-made-then-the-forwardingentity-should-be-described-in-terms-of-subordinate-parts-against-which-coherent-statements-can-be-made {
                    description "none";
                }
                feature present-if-cost-information-is-relevant-to-usage-and-statement-can-be-made-that-applies-equally-to-all-flows-that-can-be-supported-by-the-forwardingentity
note-that-if-cost-is-relevant-but-consistent-statement-cannot-be-made-then-the-forwardingentity-should-be-described-in-terms-of-subordinate-parts-against-which-coherent-statements-can-be-made {
                    description "none";
                }
                feature present-if-transfer-timing-information-is-relevant-to-usage-and-statement-can-be-made-that-applies-equally-to-all-flows-that-can-be-supported-by-the-forwardingentity
note-that-if-transfer-timing-is-relevant-but-consistent-statement-cannot-be-made-then-the-forwardingentity-should-be-described-in-terms-of-subordinate-parts-against-which-coherent-statements-can-be-made {
                    description "none";
                }
                feature present-if-transfer-capacity-information-is-relevant-to-usage-and-statement-can-be-made-that-applies-equally-to-all-flows-that-can-be-supported-by-the-forwardingentity
note-that-if-transfer-capacity-is-relevant-but-consistent-statement-cannot-be-made-then-the-forwardingentity-should-be-described-in-terms-of-subordinate-parts-against-which-coherent-statements-can-be-made {
                    description "none";
                }
                feature present-if-transfer-integrity-information-is-relevant-to-usage-and-statement-can-be-made-that-applies-equally-to-all-flows-that-can-be-supported-by-the-forwardingentity
note-that-if-transfer-integrity-is-relevant-but-consistent-statement-cannot-be-made-then-the-forwardingentity-should-be-described-in-terms-of-subordinate-parts-against-which-coherent-statements-can-be-made {
                    description "none";
                }
                feature present-if-validation-information-is-relevant-to-usage-and-statement-can-be-made-that-applies-equally-to-all-flows-that-can-be-supported-by-the-forwardingentity
note-that-if-validation-is-relevant-but-consistent-statement-cannot-be-made-then-the-forwardingentity-should-be-described-in-terms-of-subordinate-parts-against-which-coherent-statements-can-be-made
note-that-validation-may-not-be-possible-for-the-specific-layer-protocol-or-in-the-particular-case {
                    description "none";
                }
                feature present-if-layer-transition-information-is-relevant-to-usage-and-statement-can-be-made-that-applies-equally-to-all-flows-that-can-be-supported-by-the-forwardingentity
note-that-if-layer-transition-is-relevant-but-consistent-statement-cannot-be-made-then-the-forwardingentity-should-be-described-in-terms-of-subordinate-parts-against-which-coherent-statements-can-be-made
note-that-layer-transition-occurs-in-a-limited-number-of-cases {
                    description "none";
                }

            /***********************
            * package resilience
            **********************/ 
                grouping configuration-and-switch-control {
                    leaf switch-rule {
                        type to-be-defined;
                        description "A sketch of the presence of complex rules governing the switch behavior.";
                    }
                    leaf-list fc-switch {
                        type leafref {
                            path '/core-model:network-control-domain/core-model:network-element/core-model:ltp/core-model:embedded-clock/core-model:encapsulated-fc/core-model:fc-switch/core-model:';
                        }
                        description "The switch being controlled.";
                    }
                    leaf control-parameters {
                        type leafref {
                            path '/core-model:network-control-domain/core-model:network-element/core-model:ltp/core-model:embedded-clock/core-model:encapsulated-fc/core-model:configuration-and-switch-control/core-model:control-parameters/core-model:';
                        }
                        description "The control parameters to be applied if local parameters are used rather than profiles.";
                    }
                    leaf-list profile-proxy {
                        type leafref {
                            path '/core-model:profile-proxy/core-model:';
                        }
                        description "Applied profiles.";
                    }
                    container local-pac {
                        uses local-pac;
                        description "none";
                    }
                    container global-pac {
                        uses global-pac;
                        description "none";
                    }
                    leaf is-frozen {
                        type boolean;
                        description "Temporarily prevents any switch action to be taken and, as such, freezes the current state. 
                            Until the freeze is cleared, additional near-end external commands are rejected and fault condition changes and received APS messages are ignored.
                            All administrative controls of any aspect of protection are rejected.";
                    }
                    leaf is-coordinated-switching-both-ends {
                        type boolean;
                        description "The C&SC is operating such that switching at both ends of each flow across the FC is coordinated at both ingress and egress ends.";
                    }
                    leaf-list subordinate-control {
                        type leafref {
                            path '/core-model:network-control-domain/core-model:network-element/core-model:ltp/core-model:embedded-clock/core-model:encapsulated-fc/core-model:configuration-and-switch-control/core-model:';
                        }
                        description "A C&SC that is fully or partially subordinate this C&SC. 
                            A peer is considered as partially subordinate in that the peer will respond to requests for action from this C&SC but will also make requests for action to be carried out by this C&SC.
                            Where there is a peer relationship each controller in the peering will see the other controller as subordinate.";
                    }
                    leaf casc-spec {
                        type leafref {
                            path '/core-model:configuration-group-spec/core-model:forwarding-spec/core-model:casc-spec/core-model:';
                        }
                        description "none";
                    }
                    leaf-list encapsulated-casc {
                        type leafref {
                            path '/core-model:network-control-domain/core-model:network-element/core-model:ltp/core-model:embedded-clock/core-model:encapsulated-fc/core-model:configuration-and-switch-control/core-model:';
                        }
                        description "Where a C&SC is complex it may be decomposed into subordinate C&SC parts.
                            The decomposition is described by the C&SC spec.";
                    }
                    leaf-list casc-port {
                        type leafref {
                            path '/core-model:network-control-domain/core-model:network-element/core-model:ltp/core-model:embedded-clock/core-model:encapsulated-fc/core-model:configuration-and-switch-control/core-model:casc-port/core-model:';
                        }
                        description "A reference to ports of a C&SC that can be used where there is significant asymmetry to be represented.
                            The C&SC need not have ports.";
                    }
                    leaf-list coordinated-fc {
                        type leafref {
                            path '/core-model:network-control-domain/core-model:network-element/core-model:ltp/core-model:embedded-clock/core-model:encapsulated-fc/core-model:';
                        }
                        description "none";
                    }
                    leaf resilience-control-status {
                        type resilience-control;
                        description "none";
                    }
                    description "Represents the capability to control and coordinate switches, to add/delete/modify FCs and to add/delete/modify LTPs/LPs so as to realize a protection scheme.";
                }
                grouping control-parameters-pac {
                    leaf reversion-mode {
                        type reversion-mode;
                        description "Indicates whether the protection scheme is revertive or non-revertive.";
                    }
                    leaf wait-to-revert-time {
                        type uint64;
                        default "15";
                        description "If the protection system is revertive, this attribute specifies the time, in minutes, to wait after a fault clears on a higher priority (preferred) resource before switching to the preferred resource.
                            If a further fault occurs on the preferred resource in the waitToRevertTime then the reversion attempt is cancelled.
                            The WTR timer is overridden by the needs of a higher priority signal. Depending upon which resource is requested this may simply cancel the attempt to revert of may cause immediate reversion.";
                    }
                    leaf prot-type {
                        type protection-type;
                        description "Indicates the protection scheme that is used for the ProtectionGroup.";
                    }
                    leaf hold-off-time {
                        type uint64;
                        description "This attribute indicates the time, in milliseconds, between declaration of a switch trigger condition (e.g. signal degrade or signal fail), and the initialization of the protection switching algorithm.";
                    }
                    leaf network-scheme-specification {
                        type leafref {
                            path '/core-model:network-scheme-specification/core-model:';
                        }
                        description "none";
                    }
                    description "A list of control parameters to apply to a switch.";
                }
                grouping fc-route {
                    leaf-list fc {
                        type leafref {
                            path '/core-model:network-control-domain/core-model:network-element/core-model:ltp/core-model:embedded-clock/core-model:encapsulated-fc/core-model:';
                        }
                        description "The list of FCs describing the route of an FC.
                            In most cases the FcRoute has 2 or more FCs however there are some cases where a Route with one FC is valid.";
                    }
                    leaf selection-priority {
                        type uint64;
                        description "The preference priority of the resource in the resilience scheme for a particular FC. 
                            The lower the value the higher the priority.
                            A lower value of selection priority is preferred
                            If two resources have the same value they are of equal priority.
                            There is no preference between equal priorities.
                            If a resource with the lowest value selection priority fails, then the next lowest value available (may be the same value) is picked.
                            Hence on failure of the current resource the next best available will be selected.
                            If there are several equal values, the choice is essentially arbitrary).
                            If the scheme is revertive then when a resource of higher priority than the currently selected resource recovers it will be selected.
                            This is equivalent to working/protection but allows for all static scheme types with n:m capability. 
                            In simple schemes 0 = working and 1 = protecting.
                            If selection priority of a Route is increased in value and the Route is currently selecting this Route, then if another Route of a lower selection priority value is available the wait to restore process will come into action as if the other Route had just become available.
                            If selection priority of a Route is changed and the FC is not currently selecting this Route but is selecting an item that is now of a higher numeric value than the changed Route, then the wait to restore process will come into action as if the other Route had just become available.";
                    }
                    leaf route-selection-control {
                        type route-selection-control;
                        description "Degree of administrative control applied to the route selection.";
                    }
                    leaf route-selection-reason {
                        type route-selection-reason;
                        config false;
                        description "The reason for the current route selection.";
                    }
                    leaf-list link {
                        type leafref {
                            path '/core-model:link/core-model:';
                        }
                        description "none";
                    }
                    uses global-class;
                    description "Each instance of an FC Route (FcRoute) class models an individual route of an FC. The route is an alternative view of the internal structure of the FC to FC aggregation (see FcHasLowerLeverFcs association).
                        There are cases where a route is the most appropriate representation and cases where the aggregation approach is the most appropriate representation.
                        The route of an FC object is represented by a list of FCs at a lower level with the implicit understanding that unmodeled link connections are interleaved between the lower level FCs. 
                        Note that depending on the service supported by an FC, the FC can have multiple routes.
                        The FcRoute is also applicable where an NE level ForwardingDomain may be decomposed into subordinate ForwardingDomains. Applies to both virtual and real NE cases.";
                }
                grouping fc-switch {
                    leaf hold-off-time {
                        type uint64;
                        description "Moved to ControlParameter_Pac... This attribute indicates the time, in seconds, between declaration of unacceptable quality of signal on the currently selected FcPort, and the initialization of the protection switching algorithm. ";
                    }
                    leaf prot-type {
                        type protection-type;
                        description "Indicates the protection scheme that is used for the ProtectionGroup.";
                    }
                    leaf reversion-mode {
                        type reversion-mode;
                        description "Moved to ControlParameter_Pac... This attribute whether or not the protection scheme is revertive or non-revertive. ";
                    }
                    leaf-list selected-fc-port {
                        type leafref {
                            path '/core-model:network-control-domain/core-model:network-element/core-model:ltp/core-model:embedded-clock/core-model:encapsulated-fc/core-model:fc-port/core-model:';
                        }
                        description "Indicates which points are selected by the switch.
                            Depending on the switch spec (via FcSpec)
                            - more than one FcPort can be selected at any one time (e.g. egress switch, ingress packet switch)
                            - zero FcPorts can  be selected. For an ingress switch this indicates that the switch common (egress) is 'high impedance'
.";
                    }
                    leaf-list profile-proxy {
                        type leafref {
                            path '/core-model:profile-proxy/core-model:';
                        }
                        description "Provides a set of predefined values for switch control in place of the direct values available via the FcSwitch or via _configurationAndSwitchControl.";
                    }
                    leaf configuration-and-switch-control {
                        type leafref {
                            path '/core-model:network-control-domain/core-model:network-element/core-model:ltp/core-model:embedded-clock/core-model:encapsulated-fc/core-model:configuration-and-switch-control/core-model:';
                        }
                        description "A ConfigurationAndSwitchController that is external to the switch (it is coordinating many switches and hence cannot be encapsulated in the FcSwitch.";
                    }
                    leaf internal-configuration-and-switch-control {
                        type leafref {
                            path '/core-model:network-control-domain/core-model:network-element/core-model:ltp/core-model:embedded-clock/core-model:encapsulated-fc/core-model:configuration-and-switch-control/core-model:';
                        }
                        description "A ConfigurationAndSwitchController encapsulated in the FcSwitch that controls the FcSwitch alone.";
                    }
                    leaf switch-control {
                        type switch-control;
                        description "Degree of administrative control applied to the switch selection.";
                    }
                    leaf switch-selects-ports {
                        type port-direction;
                        description "Indicates whether the switch selects from ingress to the FC or to egress of the FC, or both.";
                    }
                    leaf switch-selection-reason {
                        type switch-state-reason;
                        config false;
                        description "The reason for the current switch selection.";
                    }
                    leaf control-parameters {
                        type leafref {
                            path '/core-model:network-control-domain/core-model:network-element/core-model:ltp/core-model:embedded-clock/core-model:encapsulated-fc/core-model:configuration-and-switch-control/core-model:control-parameters/core-model:';
                        }
                        description "none";
                    }
                    leaf wait-to-restore-time {
                        type uint64;
                        description "Moved to ControlParameter_Pac and changed to waitToRevert... If the protection system is revertive, this attribute specifies the amount of time, in seconds, to wait after the preferred FcPort returns to an acceptable state of operation (e.g. a fault has cleared) before restoring traffic to that preferred FcPort.";
                    }
                    uses local-class;
                    description "The FcSwitch class models the switched forwarding of traffic (traffic flow) between FcPorts and is present where there is protection functionality in the FC. 
                        If an FC exposes protection (having two or more FcPorts that provide alternative identical inputs/outputs), the FC will have one or more associated FcSwitch objects to represent the alternative flow choices visible at the edge of the FC.
                        The FC switch represents and defines a protection switch structure encapsulated in the FC and essentially 'decorates' FCs that are involved in resilience schemes that use switching in a protection mechanism. 
                        Essentially FcSwitch performs one of the functions of the Protection Group in a traditional model. It associates 2 or more FcPorts each playing the role of a Protection Unit. 
                        One or more protection, i.e. standby/backup, FcPorts provide protection for one or more working (i.e. regular/main/preferred) FcPorts where either protection or working can feed one or more protected FcPort.
                        The switch may be used in revertive or non-revertive (symmetric) mode. When in revertive mode it may define a waitToRestore time.
                        It may be used in one of several modes including source switched, destination switched, source and destination switched etc. (covering cases such as 1+1 and 1:1).
                        It may be locked out (prevented from switching), force switched or manual switched.
                        It will indicate switch state and change of state.
                        The switch can be switched away from all sources such that it becomes open and hence two coordinated switches can both feed the same LTP so long as at least one of the two is switched away from all sources (is 'open').
                        The ability for a Switch to be 'high impedance' allows bidirectional ForwardingConstructs to be overlaid on the same bidirectional LTP where the appropriate control is enabled to prevent signal conflict.
                        This ability allows multiple alternate routes to be present that otherwise would be in conflict.";
                }
                grouping casc-port {
                    leaf port-role {
                        type string;
                        description "The role of the port of a C&SC. 
                            The interpretation of the role is provided by the C&SC spec.
                            The C&SC spec will set out the role in the context of C&SC functions.
                            The role will indicate how the port relates to the associated entity, e.g. is conveying messages.";
                    }
                    leaf port-role-properties {
                        type leafref {
                            path '/core-model:network-control-domain/core-model:network-element/core-model:ltp/core-model:embedded-clock/core-model:encapsulated-fc/core-model:configuration-and-switch-control/core-model:casc-port/core-model:port-role-properties/core-model:';
                        }
                        description "A link to properties associated with the port role as defined by the CascSpec.";
                    }
                    leaf-list ltp {
                        type leafref {
                            path '/core-model:network-control-domain/core-model:network-element/core-model:ltp/core-model:';
                        }
                        description "The LTP that conveys the messages related to the port and/or is subject to control action and/or provides indications of state etc.
                            For direct association, there may be up to 2 LTPs (to account for directionality differences).
                            In the specification representation, there may be a number rules that provide further LTP relationships that are implicit in the instantiated model.";
                    }
                    leaf encapsulating-casc-port {
                        type leafref {
                            path '/core-model:network-control-domain/core-model:network-element/core-model:ltp/core-model:embedded-clock/core-model:encapsulated-fc/core-model:configuration-and-switch-control/core-model:casc-port/core-model:';
                        }
                        description "In a case where there is nested C&SC the ports are also nested and this references the superior port.";
                    }
                    leaf is-related-control-flow-disabled {
                        type boolean;
                        default "true";
                        description "If TRUE, then any Control signal flow related to this controller (to, from or drop-and-continue) is prevented from passing through the related LTP carrying the signaling for this controller.
                            This can be considered as being realized using an FcSwitch in an FC embedded in the LP at the layer of signaling to disconnect the FcPort bidirectionally.
                            This FcSwitch should be represented in the LTP spec.
                            Note that the FcSwitch will be at the granularity of the relevant control signal and other flows may be passed uninterrupted.";
                    }
                    leaf is-controlled-fc-port-disabled {
                        type boolean;
                        description "If TRUE, then the related FcPort on the FC is disabled and hence signal will not flow through that FcPort.
                            This is realized using an FcSwitch to disconnect the FcPort bidirectionally.
                            Note that as the controller may control many FCs and may switch them all together as one, in an implementation the FcSwitch could be omitted from the FC instance model.
                            Any omission should be explained by the FcSpec.
                            This is equivalent to a blocked indication on the LTP used in other representations.";
                    }
                    leaf is-protection-lock-out {
                        type boolean;
                        description "The resource is configured to temporarily not be available for use in the protection scheme(s) it is part of.
                            This overrides all other protection control states including forced.
                            If the item is locked out, then it cannot be used under any circumstances.
                            This causes isRelatedControlFlowDisabled to become TRUE and isControlledFcPortDisabled to become TRUE.";
                    }
                    description "A port of a C&SC that can be used where there is significant asymmetry to be represented.
                        This can represent any combination of:
                        - the conveying of messaging to/from the C&SC
                        - the conveying of control action
                        - the providing of indications of state etc.";
                }
                grouping casc-port-role-properties {
                    leaf signalling-format {
                        type string;
                        description "none";
                    }
                    leaf monitoring-detail {
                        type string;
                        description "none";
                    }
                    leaf control-details {
                        type string;
                        description "none";
                    }
                    description " Container for properties associated with the port role as defined by the CascSpec.";
                }

            /***********************
            * package timing
            **********************/ 
                grouping clock {
                    leaf run-mode {
                        type run-mode;
                        config false;
                        description "The run-mode of the frequency system clock, such as free-run, locked, and holdover.";
                    }
                    leaf-list encompassed-clock {
                        type leafref {
                            path '/core-model:network-control-domain/core-model:network-element/core-model:ltp/core-model:embedded-clock/core-model:';
                        }
                        description "A clock may be emergent from and may effectively encompass several clocks in a resilient solution.";
                    }
                    leaf-list encapsulated-fc {
                        type leafref {
                            path '/core-model:network-control-domain/core-model:network-element/core-model:ltp/core-model:embedded-clock/core-model:encapsulated-fc/core-model:';
                        }
                        description "A Clock may encapsulate an FC related to resilience where the clock provides an output that is essentially that of one of several other clocks in the resilience scheme.";
                    }
                    leaf-list output-ltp {
                        type leafref {
                            path '/core-model:network-control-domain/core-model:network-element/core-model:ltp/core-model:';
                        }
                        description "A clock may feed one or more LTPs with timing information to propagate across the network (it may feed no LTPs).";
                    }
                    leaf-list encapsulated-casc {
                        type leafref {
                            path '/core-model:network-control-domain/core-model:network-element/core-model:ltp/core-model:embedded-clock/core-model:encapsulated-fc/core-model:configuration-and-switch-control/core-model:';
                        }
                        description "The clock may encapsulate a complex FC where there is a resilience mechanism active and that FC will need to be controlled. 
                            The Casc to control the FC can be encapsulated in the Clock.";
                    }
                    leaf-list phase-aligned-clock {
                        type leafref {
                            path '/core-model:network-control-domain/core-model:network-element/core-model:ltp/core-model:embedded-clock/core-model:';
                        }
                        description "One or more clocks can be actively phase aligned (this is especially relevant in a hitless resilience scheme).";
                    }
                    uses local-class;
                    description "Clock function processes the input sync information (frequency and ssm or time stamp and PTP announce messages) and provides the modified sync information to the sync distribution function.
                        If none of the inputs meet the quality defined by the controller the clock may enter a hold-over or free run mode. 
                        The status of the clock will be reported to the controller.";
                }

            grouping forwarding-domain {
                leaf-list layer-protocol-name {
                    type layer-protocol-name;
                    min-elements 1;
                    description "One or more protocol layers at which the FD represents the opportunity to enable forwarding between LTP that bound it.";
                }
                leaf-list lower-level-fd {
                    type leafref {
                        path '/core-model:network-control-domain/core-model:network-element/core-model:fd/core-model:';
                    }
                    description "The FD class supports a recursive aggregation relationship (HigherLevelFdEncompassesLowerLevelFds) such that the internal construction of an FD can be exposed as multiple lower level FDs and associated Links (partitioning).
                        The aggregated FDs and Links form an interconnected topology that provides and describes the capability of the aggregating FD.
                        Note that the model actually represents an aggregation of lower level FDs into higher level FDs as views rather than FD partition, and supports multiple views. 
                        Aggregation allow reallocation of capacity from lower level FDs to different higher level FDs as if the network is reorganized  (as the association is aggregation not composition).";
                }
                leaf-list fc {
                    type leafref {
                        path '/core-model:network-control-domain/core-model:network-element/core-model:ltp/core-model:embedded-clock/core-model:encapsulated-fc/core-model:';
                    }
                    description "An FD aggregates one or more FCs. An aggregated FC connects LTPs that bound the FD.";
                }
                leaf-list ltp {
                    type leafref {
                        path '/core-model:network-control-domain/core-model:network-element/core-model:ltp/core-model:';
                    }
                    description "An instance of FD is associated with zero or more LTP objects. 
                        The LTPs that bound the FD provide capacity for forwarding.
                        For asymmetric FDs, the association to the LTP is via the FdPort.";
                }
                leaf-list lower-level-link {
                    type leafref {
                        path '/core-model:link/core-model:';
                    }
                    description "The FD encompasses Links that interconnect lower level FDs and collect Links that are wholly within the bounds of the FD.
                        See also _lowerLevelFd.";
                }
                leaf fd-rule-set {
                    type leafref {
                        path '/core-model:fd-and-link-rule-set/core-model:';
                    }
                    description "The rules related to an FD.";
                }
                leaf layer-protocol-parameter-spec {
                    type leafref {
                        path '/core-model:layer-protocol-parameter-spec/core-model:';
                    }
                    description "none";
                }
                leaf-list fd-spec {
                    type leafref {
                        path '/core-model:network-control-domain/core-model:network-element/core-model:fd/core-model:';
                    }
                    description "none";
                }
                list fd-port {
                    uses fd-port;
                    description "The association of the FD to LTPs is either made directly for symmetric FDs or via FdPort for asymmetric FDs.";
                }
                leaf-list pc {
                    type leafref {
                        path '/core-model:equipment/core-model:encapsulated-non-fru/core-model:foundation-pc/core-model:';
                    }
                    description "An FD constrains one or more PCs. A constrained PC connects LTPs on the boundary of the FD";
                }
                uses global-class;
                uses forwarding-entity;
                description "The ForwardingDomain (FD) class models the topological component that represents a forwarding capability that provides the opportunity to enable forwarding (of specific transport characteristic information at one or more protocol layers) between points.
                    The FD object provides the context for and constrains the formation, adjustment and removal of FCs and hence offers the potential to enable forwarding.
                    The FCs may be formed between LTPs at the boundary of the FD or between physical ports at the boundary of the FD (for media layers).
                    A number of FDs (related by Links) may be grouped and abstracted to form an FD where that FD represents the effect of the underlying FDs but where the detailed structure is not apparent.
                    This grouping and abstraction is potentially recursive.
                    An FD represents an abstraction of some combination of software behavior, electronic behavior and physical structure that provides a forwarding capability. 
                    At a lower level of recursion an FD could represent a forwarding capability within a device. 
                    A device may encompass two or more disjoint forwarding capabilities and may support more than one layer protocol, hence more than one FD.
                    A routing fabric may be logically partitioned to represent connectivity constraints, hence the FD representing the routing fabric may be partitioned into a number of FDs representing the constraints.
                    The FD represents a subnetwork [ITU-T G.800], FlowDomain [TMF 612] and a MultiLayerSubNetwork (MLSN) [TMF 612]. 
                    As in the TMF concept of MLSN the FD can support more than one layer-protocol.
                    Note that the ITU-T G.800 subnetwork is a single layer entity.";
            }
            grouping forwarding-construct {
                leaf layer-protocol-name {
                    type layer-protocol-name;
                    description "The layerProtocol at which the FC enables the potential for forwarding.";
                }
                leaf-list lower-level-fc {
                    type leafref {
                        path '/core-model:network-control-domain/core-model:network-element/core-model:ltp/core-model:embedded-clock/core-model:encapsulated-fc/core-model:';
                    }
                    description "An FC object supports a recursive aggregation relationship such that the internal construction of an FC can be exposed as multiple lower level FC objects (partitioning).
                        Aggregation is used as for the FD to allow changes in hierarchy. 
                        FC aggregation reflects FD aggregation. 
                        The FC represents what would have traditionally been considered as a 'Cross-Connection' in an 'NE'. The 'Cross-Connection' in an 'NE' is not necessarily the lowest level of FC partitioning.
                        ";
                }
                leaf-list fc-route {
                    type leafref {
                        path '/core-model:fc-route/core-model:';
                    }
                    description "An FC object can have zero or more routes, each of which is defined as a list of lower level FC objects describing the flow across the network.";
                }
                list fc-port {
                    min-elements 2;
                    uses fc-port;
                    description "The FcPorts define the boundary of the FC.
                        The FC is accessed via the FcPorts.
                        Flow within the FC is defined in terms of its FcPorts.";
                }
                leaf-list fc-switch {
                    type leafref {
                        path '/core-model:network-control-domain/core-model:network-element/core-model:ltp/core-model:embedded-clock/core-model:encapsulated-fc/core-model:fc-switch/core-model:';
                    }
                    description "If an FC exposes protection (having two FcPorts that provide alternative identical inputs/outputs), the FC will have one or more associated FcSwitch objects.
                        The arrangement of switches for a particular instance is described by a referenced FcSpec";
                }
                leaf-list configuration-and-switch-control {
                    type leafref {
                        path '/core-model:network-control-domain/core-model:network-element/core-model:ltp/core-model:embedded-clock/core-model:encapsulated-fc/core-model:configuration-and-switch-control/core-model:';
                    }
                    description "Reference to a ConfigurationAndSwitchController that coordinates switches encapsulated in the FC.
                        The controller coordinates multiple switches in the same FC.";
                }
                leaf forwarding-direction {
                    type forwarding-direction;
                    description "The directionality of the ForwardingConstruct. 
                        Is applicable to simple ForwardingConstructs where all FcPorts are BIDIRECTIONAL (the ForwardingConstruct will be BIDIRECTIONAL) or UNIDIRECTIONAL (the ForwardingConstruct will be UNIDIRECTIONAL). 
                        Is not present in more complex cases.
                        In the case of media the FcPorts and FC may also be omni-directional.";
                }
                leaf is-protection-lock-out {
                    if-feature in-protection-context-if-server-of-protection-where-entire-server-is-to-be-excluded-from-use-for-protection;
                    type boolean;
                    description "The resource is configured to temporarily not be available for use in the protection scheme(s) it is part of.
                        This overrides all other protection control states including forced.
                        If the item is locked out then it cannot be used under any circumstances.
                        Note: Only relevant when part of a protection scheme.";
                }
                leaf service-priority {
                    type uint64;
                    description "Relevant where 'service' FCs are competing for server resources.
                        Used to determine which signal FC is allocated resource. 
                        The priority of the 'service' with respect to other 'services'. 
                        Lower numeric value means higher priority. 
                        Covers cases such as pre-emptible in a resilience solution. ";
                }
                list fc-spec-reference-class-ref {
                    if-feature spectargetclass-forwardingconstruct;
                    min-elements 1;
                    uses metaclass-class;
                    description "Reference to the Spec (Class).";
                }
                leaf-list supported-link {
                    type leafref {
                        path '/core-model:link/core-model:';
                    }
                    description "An FC that spans between LTPs that terminate the LayerProtocol usually supports one or more links in the client layer.";
                }
                uses global-class;
                uses forwarding-entity;
                description "The ForwardingConstruct (FC) class models enabled constrained potential for forwarding between two or more FcPorts at a particular specific layerProtocol .
                    Like the LTP, the FC supports any transport protocol including all analogue, circuit and packet forms.
                    For digital layer networks it is used to effect forwarding of transport characteristic (layer protocol) information.
                    An FC can be in only one ForwardingDomain (FD).
                    The FC is a forwarding entity.
                    At a low level of the recursion, a FC represents a cross-connection within an NE. It may also represent a fragment of a cross-connection under certain circumstances.
                    The FC object can be used to represent many different structures including point-to-point (P2P), point-to-multipoint (P2MP), rooted-multipoint (RMP) and multipoint-to-multipoint (MP2MP) bridge and selector structures for linear, ring or mesh protection schemes.
                    When applied to media, the FC represents the ability for a flow/wave (potentially containing information), to be propagated between FcPorts. 
                    The existence of a FC instance is independent of the presence (or absence) of a flow/wave (and any information encoded within it).  
                    A flow/wave cannot propagate in the absence of a FC instance.";
            }
            grouping network-control-domain {
                leaf-list fd {
                    type leafref {
                        path '/core-model:network-control-domain/core-model:network-element/core-model:fd/core-model:';
                    }
                    description "The FDs accessible via the NCD.";
                }
                leaf-list link {
                    type leafref {
                        path '/core-model:link/core-model:';
                    }
                    description "The links accessible in the scope of the NCD. 
                        The domain is bounded by off-network links.";
                }
                leaf-list network-element {
                    type leafref {
                        path '/core-model:network-control-domain/core-model:network-element/core-model:';
                    }
                    description "The network elements within the scope of the NCD where each NE is within one and only one domain.";
                }
                uses global-class;
                description "The Network Control Domain (NCD) class represents the scope of control that a particular SDN controller has with respect to a particular network, (i.e., encompassing a designated set of interconnected network elements).
                    In the interfaces between SDN controllers where virtualization is necessary, e.g., in client/server SDN controller relationship, the NCD object defines the scope of control of the client SDN controller on the virtual network that has been provided by the server SDN controller (i.e., the scope of control relates to the partitioned provider resources allocated to that particular client). 
                    The NCD provides the scope of naming space for identifying objects representing the virtual resources within the virtual network.";
            }
            grouping link {
                leaf-list layer-protocol-name {
                    type layer-protocol-name;
                    min-elements 1;
                    description "The Link can support multiple transport layer protocols via the associated LTP object. 
                        For implementation optimization, where appropriate, multiple layer-specific Links can be merged and represented as a single Link instance as the Link can represent a list of layer protocols.
                        A Link may support different layer protocols at each Port when it is a transitional Link.";
                }
                leaf-list fd {
                    type leafref {
                        path '/core-model:network-control-domain/core-model:network-element/core-model:fd/core-model:';
                    }
                    min-elements 2;
                    description "The Link associates with two or more FDs. 
                        This association provides a direct summarization of the association via LinkPort and LTP.";
                }
                list link-port {
                    min-elements 2;
                    uses link-port;
                    description "The association of the Link to LTPs is made via LinkPort (essentially the ports of the Link).";
                }
                leaf-list lower-level-link {
                    type leafref {
                        path '/core-model:link/core-model:';
                    }
                    description "A Link may be formed from subordinate links (similar FD formations from subordinate FDs). This association is intended to cover concepts such as serial compound links. ";
                }
                leaf link-direction {
                    type forwarding-direction;
                    description "The directionality of the Link. 
                        Is applicable to simple Links where all LinkPorts are BIDIRECTIONAL (the Link will be BIDIRECTIONAL) or UNIDIRECTIONAL (the Link will be UNIDIRECTIONAL). 
                        Is not present in more complex cases.";
                }
                leaf fd-rule-set {
                    type leafref {
                        path '/core-model:fd-and-link-rule-set/core-model:';
                    }
                    description "The rules related to a Link.";
                }
                leaf is-protection-lock-out {
                    if-feature in-protection-context-if-server-of-protection-where-entire-server-is-to-be-excluded-from-use-for-protection;
                    type boolean;
                    description "The resource is configured to temporarily not be available for use in the protection scheme(s) it is part of.
                        This overrides all other protection control states including forced.
                        If the item is locked out, then it cannot be used under any circumstances.
                        Note: Only relevant when part of a protection scheme.";
                }
                leaf-list fc {
                    type leafref {
                        path '/core-model:network-control-domain/core-model:network-element/core-model:ltp/core-model:embedded-clock/core-model:encapsulated-fc/core-model:';
                    }
                    description "A Link contains one or more FCs. A contained FC connects LTPs that bound the Link. 
                        This FC represents the traditional link connection. It is often not supported in implementations as it can be inferred from FCs in the corresponding FDs.";
                }
                leaf-list lower-level-fd {
                    type leafref {
                        path '/core-model:network-control-domain/core-model:network-element/core-model:fd/core-model:';
                    }
                    description "FD(s) that form part of a serial compound Link.";
                }
                leaf link-spec {
                    type leafref {
                        path '/core-model:link/core-model:';
                    }
                    description "none";
                }
                list link-spec-reference-class-ref {
                    if-feature spectargetclass-link;
                    min-elements 1;
                    uses metaclass-class;
                    description "none";
                }
                uses global-class;
                uses forwarding-entity;
                description "The Link class models effective adjacency between two or more ForwardingDomains (FD). 
                    For digital layer networks, in its basic form (i.e., point-to-point Link) it associates a set of LTP clients on one FD with an equivalent set of LTP clients on another FD. 
                    Like the FC, the Link has ports (LinkPort) which take roles relevant to the constraints on flows offered by the Link (e.g., Root role or leaf role for a Link that has a constrained Tree configuration).";
            }
            grouping network-element {
                leaf-list fd {
                    type leafref {
                        path '/core-model:network-control-domain/core-model:network-element/core-model:fd/core-model:';
                    }
                    description "Represents the FD that is completely within the boundary of the NE.
                        At a low level of recursion, an FD (within a network element (NE)) represents a switch matrix (i.e., a fabric). 
                        Note that an NE can encompass multiple switch matrices (FDs) and the FD representing the switch matrix can be further partitioned.
                        Where an FD is referenced by the NeEncompassesFd association, any FDs that it encompasses (i.e., that are associated with it by HigherLevelFdEncompassesLowerLevelFds), must also be encompassed by the NE and hence must have the NeEncompassesFd association.
                        ";
                }
                leaf-list ltp {
                    type leafref {
                        path '/core-model:network-control-domain/core-model:network-element/core-model:ltp/core-model:';
                    }
                    description "An NE has associated LTPs that are at its boundary.
                        The NeEncompassesFd association occurs for FDs that are within the bounds of the NetworkElement definition such that the FD is bounded by LTPs, all of which are on the boundary of the NetworkElement or are within the NetworkElement. 
                        An LTP can be independent of an NE.";
                }
                uses global-class;
                description "The Network Element (NE) class represents a network element (traditional NE) in the data plane.
                    A data plane network element is essentially a consolidation of capabilities that can be viewed and controlled through a 'single' management-control port.
                    In the direct interface from an SDN controller to a network element in the data plane, the NetworkElement object defines the scope of control for the resources within the network element
                    For example internal transfer of user information between the external terminations (ports of the NE), encapsulation, multiplexing/demultiplexing, and OAM functions, etc. 
                    The NetworkElement provides the scope of the naming space for identifying objects representing the resources within the data plane network element.
                    NE is really a product bundling or some view of management scope, management access, session. 
                    The NE is not directly part of topology but brings meaning to the FD context and the LTP context (and hence the links). ";
            }
            grouping sdn-controller {
                uses global-class;
                description "Represents the SDN controller.";
            }
            grouping fc-port {
                leaf-list ltp {
                    type leafref {
                        path '/core-model:network-control-domain/core-model:network-element/core-model:ltp/core-model:';
                    }
                    max-elements 2;
                    description "The FcPort may be associated with more than one LTP when the FcPort is bidirectional and the LTPs are unidirectional.
                        Multiple LTP
                        - Bidirectional FcPort to two Uni-directional LTPs
                        Zero LTP
                        - BreakBeforeMake transition
                        - Planned LTP not yet in place
                        - Off-network LTP referenced through other mechanism.";
                }
                leaf role {
                    type port-role;
                    description "Each FcPort of the FC has an assigned role (e.g., working, protection, protected, symmetric, hub, spoke, leaf, root) in the context of the FC with respect to the FC function. 
                        The role is fixed by the referenced FcSpec.";
                }
                leaf fc-port-direction {
                    type port-direction;
                    description "The orientation of the defined flow at the FcPort.";
                }
                leaf is-protection-lock-out {
                    if-feature in-protection-context-where-the-fcport-is-to-be-excluded-from-use-for-protection;
                    type boolean;
                    description "The resource is configured to temporarily not be available for use in the protection scheme(s) it is part of.
                        This overrides all other protection control states including forced.
                        If the item is locked out, then it cannot be used under any circumstances.
                        Note: Only relevant when part of a protection scheme.";
                }
                leaf selection-priority {
                    type uint64;
                    description "The preference priority of the resource in the protection scheme for a particular FC. 
                        The lower the value the higher the priority.
                        A lower value of selection priority is preferred
                        If two resources have the same value they are of equal priority.
                        There is no preference between equal priorities.
                        If a resource with the lowest value selection priority fails,, then the next lowest value available (may be the same value) is picked.
                        Hence on failure of the current resource the next best available will be selected.
                        If there are several equal values, the choice is essentially arbitrary.
                        If the scheme is revertive then when a resource of higher priority than the currently selected resource recovers it will be selected.
                        This is equivalent to working/protection but allows for all static scheme types with n:m capability. 
                        In simple schemes 0 = working and 1 = protecting.
                        If selection priority of an FcPort is increased in value and the FC is currently selecting this FcPort then if another FcPort of a lower selection priority value is available, the wait to restore process will come into action as if the other FcPort had just become available.
                        If selection priority of a FcPort is changed and the FC is not currently selecting this FcPort but is selecting an item that is now of a higher numeric value than the changed FcPort then the wait to restore process will come into action as if the other FcPort had just become available.";
                }
                leaf is-internal-port {
                    type boolean;
                    config false;
                    description "The FcPort is not exposed and cannot have associated LTPs.
                        This form of FcPort is used to enable chaining of FcSwitches or FcRoutes in complex network protection scenarios.";
                }
                leaf-list fc-route-feeds-fc-port-egress {
                    type leafref {
                        path '/core-model:fc-route/core-model:';
                    }
                    description "Identifies which route(s) currently actively forward to the FcPort to exit the FC to an LTP (or for an internal FcPort to propagate to the next internal switch/route).";
                }
                leaf-list fc-port {
                    type leafref {
                        path '/core-model:network-control-domain/core-model:network-element/core-model:ltp/core-model:embedded-clock/core-model:encapsulated-fc/core-model:fc-port/core-model:';
                    }
                    max-elements 2;
                    description "An FcPort may have a direct association to another FcPort where there is a transition from one domain to another but where there has been no termination.";
                }
                leaf-list port-of-internal-fc {
                    type leafref {
                        path '/core-model:network-control-domain/core-model:network-element/core-model:ltp/core-model:embedded-clock/core-model:encapsulated-fc/core-model:fc-port/core-model:';
                    }
                    description "none";
                }
                leaf pin {
                    type leafref {
                        path '/core-model:field-replaceable/core-model:connector/core-model:pin/core-model:';
                    }
                    description "For media FCs, the name of the pin that terminates the media.";
                }
                uses local-class;
                description "The association of the FC to LTPs is always made via FcPorts.
                    In the case of media the association between FCs is made via their FcPorts and the association of an FC to the physical Pin is made via the FcPort.
                    The FcPort class models the access to the FC function. 
                    The traffic forwarding between the associated FcPorts of the FC depends upon the type of FC and may be associated with FcSwitch object instances.  
                    In cases where there is resilience, the FcPort may convey the resilience role of the access to the FC. 
                    It can represent a protected (resilient/reliable) point or a protecting (unreliable working or protection) point.
                    The FcPort replaces the Protection Unit of a traditional protection model. 
                    The ForwardingConstruct can be considered as a component and the FcPort as a Port on that component.";
            }
            grouping layer-protocol {
                leaf layer-protocol-name {
                    type layer-protocol-name;
                    description "Indicate the specific layer-protocol described by the LayerProtocol entity.";
                }
                leaf configured-client-capacity {
                    type to-be-defined;
                    description "Provides a summarized view of the client capacity that is configurable for use.
                        Note the client LTP association should provide all necessary detail hence this attribute is questionable.";
                }
                leaf lp-direction {
                    type termination-direction;
                    description "The overall directionality of the LP. 
                        - A BIDIRECTIONAL LP will have some SINK and/or SOURCE flows.
                        - A SINK LP can only contain elements with SINK flows or CONTRA_DIRECTION_SOURCE flows
                        - A SOURCE LP can only contain SOURCE flows or CONTRA_DIRECTION_SINK flows";
                }
                leaf termination-state {
                    type termination-state;
                    description "Indicates whether the layer is terminated and if so how.";
                }
                leaf-list configuration-and-switch-control {
                    type leafref {
                        path '/core-model:network-control-domain/core-model:network-element/core-model:ltp/core-model:embedded-clock/core-model:encapsulated-fc/core-model:configuration-and-switch-control/core-model:';
                    }
                    description "A switch controller external to the LayerProtocol.
                        The controller will coordinate one or more switches in one or more FCs related to the LayerProtocol";
                }
                leaf is-protection-lock-out {
                    type boolean;
                    description "The resource is configured to temporarily not be available for use in the protection scheme(s) it is part of.
                        This overrides all other protection control states including forced.
                        If the item is locked out, then it cannot be used under any circumstances.
                        Note: Only relevant when part of a protection scheme.";
                }
                leaf fc-blocks-signal-to-lp {
                    type block-direction;
                    description "none";
                }
                list lp-spec-reference-class-ref {
                    if-feature spectargetclass:-layerprotocol;
                    uses metaclass-class;
                    description "none";
                }
                uses local-class;
                description "The projection of an LTP into each transport layer is represented by a LayerProtocol (LP) instance. A LayerProtocol instance can be used for controlling termination and monitoring functionality. 
                    It can also be used for controlling the adaptation (i.e. encapsulation and/or multiplexing of client signal), tandem connection monitoring, traffic conditioning and/or shaping functionality at an intermediate point along a connection. 
                    Where the client – server relationship is fixed 1:1 and immutable, the layers can be encapsulated in a single LTP instance. Where there is a n:1 relationship between client and server, the layers must be split over two separate instances of LTP. ";
            }
            grouping logical-termination-point {
                leaf-list server-ltp {
                    type leafref {
                        path '/core-model:network-control-domain/core-model:network-element/core-model:ltp/core-model:';
                    }
                    description "References contained LTPs representing servers of this LTP in an inverse multiplexing configuration (e.g. VCAT).";
                }
                leaf-list client-ltp {
                    type leafref {
                        path '/core-model:network-control-domain/core-model:network-element/core-model:ltp/core-model:';
                    }
                    description "References contained LTPs representing client traffic of this LTP for normal cases of multiplexing.";
                }
                leaf-list lp {
                    type leafref {
                        path '/core-model:network-control-domain/core-model:network-element/core-model:ltp/core-model:lp/core-model:';
                    }
                    min-elements 1;
                    description "Ordered list of LayerProtocols that this LTP is comprised of where the first entry in the list is the lowest server layer (e.g. physical).";
                }
                leaf connected-ltp {
                    type leafref {
                        path '/core-model:network-control-domain/core-model:network-element/core-model:ltp/core-model:';
                    }
                    description "Applicable in a simple context where two LTPs are associated via a non-adjustable enabled forwarding.
                        Reduces clutter removing the need for two additional LTPs and an FC with a pair of FcPorts.";
                }
                leaf peer-ltp {
                    type leafref {
                        path '/core-model:network-control-domain/core-model:network-element/core-model:ltp/core-model:';
                    }
                    description "References contained LTPs representing the reversal of orientation of flow where two LTPs are associated via a non-adjustable enabled forwarding and where the referenced LTP is fully dependent on this LTP.";
                }
                leaf-list physical-port-reference {
                    type string;
                    description "One or more text labels for the unmodeled physical port associated with the LTP.
                        In many cases there is no associated physical port.";
                }
                leaf-list ltp-in-other-view {
                    type leafref {
                        path '/core-model:network-control-domain/core-model:network-element/core-model:ltp/core-model:';
                    }
                    description "References one or more LTPs in other views that represent this LTP. 
                        The referencing LTP is the provider of capability.";
                }
                leaf ltp-direction {
                    type termination-direction;
                    description "The overall directionality of the LTP. 
                        - A BIDIRECTIONAL LTP must have at least some LPs that are BIDIRECTIONAL but may also have some SINK and/or SOURCE LPs.
                        - A SINK LTP can only contain SINK LPs
                        - A SOURCE LTP can only contain SOURCE LPs";
                }
                leaf access-port {
                    type leafref {
                        path '/core-model:access-port/core-model:';
                    }
                    description "Provides a reference to the place where the signal is accessed. 
                        It may represent a physical place (some part of one or more connectors) or a virtual equivalent where there is no further protocol layering (visible).";
                }
                leaf transfer-capacity-pac {
                    type leafref {
                        path '/core-model:network-control-domain/core-model:network-element/core-model:ltp/core-model:transfer-capacity-pac/core-model:';
                    }
                    description "The LTP has as an inherent capacity derived from underlying capability.
                        The capacity of a particular LTP may be dependent upon other uses of resource in the device and hence it may vary over time.
                        The capacity of a Link is dependent upon the capacity of the LTPs at its ends.
                        An LTP may be an abstraction and virtualization of a subset of the underlying capability offered in a view or may be directly reflecting the underlying realization.";
                }
                list ltp-spec-reference-class-ref {
                    if-feature spectargetclass:-logicalterminationpoint;
                    min-elements 1;
                    uses metaclass-class;
                    description "Provides a reference to a specification which is in the form of a class definition.
                        An instance of LTP will reference a class (by a universally unique id) that provides definition that extends the LTP including attributes and structure that are present in the LTP instance but that are not defined in the native LTP class.
                        ";
                }
                leaf-list fd-rule-group {
                    type leafref {
                        path '/core-model:network-control-domain/core-model:network-element/core-model:fd/core-model:';
                    }
                    description "An LTP can reference FD rules that the FD that aggregates it also references so that the rules can then apply to the LTP.";
                }
                leaf-list embedded-clock {
                    type leafref {
                        path '/core-model:network-control-domain/core-model:network-element/core-model:ltp/core-model:embedded-clock/core-model:';
                    }
                    description "none";
                }
                uses global-class;
                description "The LogicalTerminationPoint (LTP) class encapsulates the termination and adaptation functions of one or more transport layers represented by instances of LayerProtocol.
                    The encapsulated transport layers have a simple fixed 1:1 client-server relationship defined by association end ordering.
                    The structure of LTP supports all transport protocols including circuit and packet forms.";
            }
            grouping link-port {
                leaf-list ltp {
                    type leafref {
                        path '/core-model:network-control-domain/core-model:network-element/core-model:ltp/core-model:';
                    }
                    description "The LinkPort may be associated with more than one LTP when the LinkPort is bidirectional and the LTPs are unidirectional.
                        Multiple LTP
                        - Bidirectional LinkPort to two Uni-directional LTPs
                        Zero LTP
                        - BreakBeforeMake transition
                        - Planned LTP not yet in place
                        - Off-network LTP referenced through other mechanism.";
                }
                leaf role {
                    type port-role;
                    description "Each LinkPort of the Link has a role (e.g., symmetric, hub, spoke, leaf, root) in the context of the Link with respect to the Link capability. ";
                }
                leaf off-network-address {
                    type string;
                    description "A freeform opportunity to express a reference for a Port of the Link that is not visible and hence is outside the scope of the control domain (off-network).
                        This attribute is expected to convey a foreign identifier/name/address or a shared reference for some mid-span point at the boundary between two administrative domains.
                        This is a reference shared between the parties either side of the network boundary. 
                        The assumption is that the provider knows the mapping between network port and offNetworkAddress and the client knows the mapping between the client port and the offNetworkAddress and that the offNetworkAddress references some common point or pool of points. 
                        It may represent some physical location where the hand-off takes place. This attribute is used when an LTP cannot be referenced.
                        A Link with an Off-network end cannot be encompassed by an FD.";
                }
                leaf link-port-direction {
                    type port-direction;
                    description "The orientation of the defined flow at the LinkPort.";
                }
                leaf-list fc-port {
                    type leafref {
                        path '/core-model:network-control-domain/core-model:network-element/core-model:ltp/core-model:embedded-clock/core-model:encapsulated-fc/core-model:fc-port/core-model:';
                    }
                    description "Where a Link supports FCs each LinkPort of that Link supports the corresponding FcPorts.";
                }
                uses local-class;
                description "The association of the Link to LTPs is made via LinkPort.
                    The LinkPort class models the access to the Link function. 
                    The traffic forwarding between the associated LinkPorts of the Link depends upon the type of Link.  
                    In cases where there is resilience, the LinkPort may convey the resilience role of the access to the Link. 
                    The Link can be considered as a component and the LinkPort as a Port on that component.";
            }
            grouping fd-port {
                leaf-list ltp {
                    type leafref {
                        path '/core-model:network-control-domain/core-model:network-element/core-model:ltp/core-model:';
                    }
                    max-elements 2;
                    description "An instance of FD is associated with zero or more LTP objects. 
                        The LTPs that bound the FD provide capacity for forwarding.
                        For asymmetric FDs, the association to the LTP is via the FdPort.";
                }
                leaf role {
                    type port-role;
                    description "Each FdPort of the FD has a role (e.g., symmetric, hub, spoke, leaf, root) in the context of the FD with respect to the FD capability. ";
                }
                leaf fd-port-direction {
                    type port-direction;
                    description "The orientation of the defined flow at the FdPort.";
                }
                leaf-list fc-port {
                    type leafref {
                        path '/core-model:network-control-domain/core-model:network-element/core-model:ltp/core-model:embedded-clock/core-model:encapsulated-fc/core-model:fc-port/core-model:';
                    }
                    description "Where an FD is asymmetric and hence has FdPorts and where that FD and supports FCs, appropriate FdPorts of that FD support the corresponding FcPorts.";
                }
                leaf pin {
                    type leafref {
                        path '/core-model:field-replaceable/core-model:connector/core-model:pin/core-model:';
                    }
                    description "For media, a pin on the boundary of the FD.";
                }
                leaf-list fd-port {
                    type leafref {
                        path '/core-model:network-control-domain/core-model:network-element/core-model:fd/core-model:fd-port/core-model:';
                    }
                    max-elements 2;
                    description "An FdPort may have a direct association to another FdPort where there is a transition from one domain to another but where there has been no termination.";
                }
                uses local-class;
                description "The association of the FD to LTPs may be direct for symmetric FDs and may be via FdPort for asymmetric FDs.
                    The FdPort class models the role of the access to the FD function. 
                    The capability to set up FCs between the associated FdPorts of the FD depends upon the type of FD. It is asymmetry in this capability that brings the need for FdPort.  
                    The FD can be considered as a component and the FdPort as a Port on that component.";
            }
            feature in-protection-context-if-server-of-protection-where-entire-server-is-to-be-excluded-from-use-for-protection {
                description "none";
            }
            feature spectargetclass-forwardingconstruct {
                description "none";
            }
            feature spectargetclass-link {
                description "none";
            }
            feature in-protection-context-where-the-fcport-is-to-be-excluded-from-use-for-protection {
                description "none";
            }
            feature spectargetclass:-layerprotocol {
                description "none";
            }
            feature spectargetclass:-logicalterminationpoint {
                description "none";
            }

        /***********************
        * package diagrams
        **********************/ 

        /***********************
        * package associations
        **********************/ 


    /***********************
    * package core-foundation-model
    **********************/ 
        /***********************
        * package type-definitions
        **********************/ 
            identity PORT_DIRECTION {
                description "none";
            }
            identity PORT_DIRECTION_BIDIRECTIONAL {
                base port-direction;
                description "The Port has both an INPUT flow and an OUTPUT flow defined.";
            }
            identity PORT_DIRECTION_INPUT {
                base port-direction;
                description "The Port only has definition for a flow into the Forwarding entity (i.e. an ingress flow).";
            }
            identity PORT_DIRECTION_OUTPUT {
                base port-direction;
                description "The Port only has definition for a flow out of the Forwarding entity (i.e. an egress flow).";
            }
            identity PORT_DIRECTION_UNIDENTIFIED_OR_UNKNOWN {
                base port-direction;
                description "Not a normal state. The system is unable to determine the correct value.";
            }
            identity PORT_DIRECTION_OMNIDIRECTIONAL {
                base port-direction;
                description "none";
            }
            identity FORWARDING_DIRECTION {
                description "none";
            }
            identity FORWARDING_DIRECTION_BIDIRECTIONAL {
                base forwarding-direction;
                description "The Forwarding entity supports both BIDIRECTIONAL flows at all Ports (i.e. all Ports have both an INPUT flow and an OUTPUT flow defined).";
            }
            identity FORWARDING_DIRECTION_UNIDIRECTIONAL {
                base forwarding-direction;
                description "The Forwarding entity has Ports that are either INPUT or OUTPUT. It has no BIDIRECTIONAL Ports.";
            }
            identity FORWARDING_DIRECTION_UNDEFINED_OR_UNKNOWN {
                base forwarding-direction;
                description "Not a normal state. The system is unable to determine the correct value.";
            }
            identity FORWARDING_DIRECTION_OMNIDIRECTIONAL {
                base forwarding-direction;
                description "none";
            }
            identity TERMINATION_DIRECTION {
                description "none";
            }
            identity TERMINATION_DIRECTION_BIDIRECTIONAL {
                base termination-direction;
                description "A Termination with both SINK and SOURCE flows.";
            }
            identity TERMINATION_DIRECTION_SINK {
                base termination-direction;
                description "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base termination-direction;
                description "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base termination-direction;
                description "Not a normal state. The system is unable to determine the correct value.";
            }
            identity EXTENDED_TERMINATION_DIRECTION {
                description "none";
            }
            identity EXTENDED_TERMINATION_DIRECTION_CONTRA_DIRECTION_SINK {
                base extended-termination-direction;
                description "The essential flow of the Termination entity is SINK (i.e. up the layer stack) but the INPUT flow of the Termination entity was provided by a SOURCE OUTPUT or taken from a SOURCE INPUT (duplicating the input signal) hence reversing the flow orientation from down the layer stack to up the layer stack.";
            }
            identity EXTENDED_TERMINATION_DIRECTION_CONTRA_DIRECTION_SOURCE {
                base extended-termination-direction;
                description "The essential flow of the Termination entity is SOURCE (i.e. down the layer stack) but the OUTPUT flow of the Termination entity was fed to (and replaces) a SINK OUTPUT or was fed to a SINK INPUT (replacing the normal flow) hence reversing the flow orientation from down the layer stack to up the layer stack.";
            }
            identity TERMINATION_STATE {
                description "none";
            }
            identity TERMINATION_STATE_LP_CAN_NEVER_TERMINATE {
                base termination-state;
                description "A non-flexible case that can never be terminated.";
            }
            identity TERMINATION_STATE_LP_NOT_TERMINATED {
                base termination-state;
                description "A flexible termination that can terminate but is currently not terminated.";
            }
            identity TERMINATION_STATE_TERMINATED_SERVER_TO_CLIENT_FLOW {
                base termination-state;
                description "A flexible termination that is currently terminated for server to client flow only.";
            }
            identity TERMINATION_STATE_TERMINATED_CLIENT_TO_SERVER_FLOW {
                base termination-state;
                description "A flexible termination that is currently terminated for client to server flow only.";
            }
            identity TERMINATION_STATE_TERMINATED_BIDIRECTIONAL {
                base termination-state;
                description "A flexible termination that is currently terminated in both directions of flow.";
            }
            identity TERMINATION_STATE_LP_PERMENANTLY_TERMINATED {
                base termination-state;
                description "A non-flexible termination that is always terminated (in both directions of flow for a bidirectional case and in the one direction of flow for both unidirectional cases).";
            }
            identity TERMINATION_STATE_TERMINATION_STATE_UNKNOWN {
                base termination-state;
                description "There TerminationState cannot be determined.";
            }
            identity PROTECTION_REASON {
                description "none";
            }
            identity PROTECTION_REASON_WAIT_TO_REVERT {
                base protection-reason;
                description "The resource is selected as control is waiting to restore to a preferred resource.";
            }
            identity PROTECTION_REASON_SIGNAL_DEGRADE {
                base protection-reason;
                description "The resource is selected as the best preferred resource is in signal degrade.";
            }
            identity PROTECTION_REASON_SIGNAL_FAIL {
                base protection-reason;
                description "The resource is selected as the best preferred resource is in signal fail.";
            }
            identity ROUTE_SELECTION_CONTROL {
                description "none";
            }
            identity ROUTE_SELECTION_CONTROL_LOCK_OUT {
                base route-selection-control;
                description "The resource is configured to temporarily not be available for use in the protection scheme(s) it is part of.
                    This overrides all other protection control states including forced.
                    If the item is locked out, then it cannot be used under any circumstances.
                    Note: Only relevant when part of a protection scheme.
                    Note: if a protection process that has a relationship to the item (i.e. is one of the options the protection process may choose) is deactivated by being isFrozen = true) then the lockout request will be rejected. ";
            }
            identity ROUTE_SELECTION_REASON {
                description "none";
            }
            identity SWITCH_CONTROL {
                description "none";
            }
            identity SWITCH_CONTROL_NORMAL {
                base switch-control;
                description "No administrative control applied to the switch.";
            }
            identity SWITCH_CONTROL_MANUAL {
                base switch-control;
                description "Resource temporarily chosen by control configuration where the resource is not the preferred resource.
                    Preferred resource has highest priority.
                    Temporarily overrides reversion.
                    If this resource fails, it will switch to best available resource. 
                    If resource selected is shared and another FC requires the resource, then the selection control will change to Normal and switch to best available based upon normal rules.
                    Cannot manually switch a Forced switch, cannot remove a forced switch, cannot switch to a locked out item and will be rejected if the protection process is deactivated by being Freeze = true).
                    A manual switch/route that is selecting an FcPort, LTP, FC, Link or Route that is subsequently set to LOCK_OUT will have the manual removed (changed to NORMAL) and will switch away from the  FcPort with LOCK_OUT to best available based upon normal rules.
                    A manual switch that is selecting an FcPort that is subsequently selected by a Forced switch will be restored to normal operation and the manual will be removed.
                    A manual switch/route that is selecting an FcPort, LTP, FC, Link or Route that is subsequently manual selected by another switch/route  will have the manual removed and will switch away from the FcPort.
                    Can be returned to NORMAL by configuration action.";
            }
            identity SWITCH_CONTROL_FORCED {
                base switch-control;
                description "Resource temporarily chosen by control configuration where the resource is not the preferred resource.
                    Preferred resource has highest priority.
                    Temporarily overrides reversion.
                    If this resource fails it will NOT switch. 
                    If resource selected is shared and another FC requires the resource through a FORCE on that FC and the FC is of a higher FcPriority then the selection control on this FC will change to NORMAL and switch to best available based upon normal rules.
                    If the resource selected is then set to LOCK_OUT then the selection control will change to NORMAL and switch to best available based upon normal rules.
                    Can be returned to NORMAL by configuration action.";
            }
            identity SWITCH_STATE_REASON {
                description "none";
            }
            identity REVERSION_MODE {
                description "none";
            }
            identity REVERSION_MODE_REVERTIVE {
                base reversion-mode;
                description "An FC switched to a lower priority (non-preferred) resource will revert to a higher priority (preferred) resource when that recovers (potentially after some hold-off time).";
            }
            identity REVERSION_MODE_NON-REVERTIVE {
                base reversion-mode;
                description "An FC switched to a lower priority (non-preferred) resource will not revert to a higher priority (preferred) resource when that recovers.";
            }
            identity RESILIENCE_CONTROL {
                description "none";
            }
            identity RESILIENCE_CONTROL_QUIESCENT {
                base resilience-control;
                description "none";
            }
            identity RESILIENCE_CONTROL_RESTORING {
                base resilience-control;
                description "none";
            }
            identity RESILIENCE_CONTROL_RECOVERY_FAILED {
                base resilience-control;
                description "none";
            }
            identity RESILIENCE_CONTROL_UNKNOWN {
                base resilience-control;
                description "none";
            }
            identity RUN_MODE {
                description "none";
            }
            identity RUN_MODE_FREE_RUN {
                base run-mode;
                description "The ckock is not synchronized to another clock.";
            }
            identity RUN_MODE_LOCKED {
                base run-mode;
                description "The clock is synchronised to another clock.";
            }
            identity RUN_MODE_HOLD_OVER {
                base run-mode;
                description "The clock was previously synchonised to another clock but that timing input has been lost.
                    The clock is set to the last known synchronization.";
            }
            identity OPERATIONAL_STATE {
                description "none";
            }
            identity OPERATIONAL_STATE_DISABLED {
                base operational-state;
                description "The resource is unable to meet the SLA of the user of the resource. 
                    If no (explicit) SLA is defined the resource is disabled if it is totally inoperable and unable to provide service to the user.";
            }
            identity OPERATIONAL_STATE_ENABLED {
                base operational-state;
                description "The resource is partially or fully operable and available for use.";
            }
            identity ADMINISTRATIVE_STATE {
                description "none";
            }
            identity ADMINISTRATIVE_STATE_LOCKED {
                base administrative-state;
                description "Users are administratively prohibited from making use of the resource.";
            }
            identity ADMINISTRATIVE_STATE_UNLOCKED {
                base administrative-state;
                description "Users are allowed to use the resource.";
            }
            identity ADMINISTRATIVE_STATE_SHUTTING_DOWN {
                base administrative-state;
                description "The entity is administratively restricted to existing instances of use only. There may be specific actions to remove existing uses. No new instances of use can be enabled.
                    The resource automatically transitions to “locked” when the last user quits. 
                    The administrative state is not visible in the client context. 
                    The lifecycle state “pending removal” should be used to indicate to the client that the provider intends to remove the resource.";
            }
            identity ADMINISTRATIVE_CONTROL {
                description "none";
            }
            identity ADMINISTRATIVE_CONTROL_UNLOCK {
                base administrative-control;
                description "The intention is for the entity to become unlocked.
                    The entity may already be UNLOCKED.";
            }
            identity ADMINISTRATIVE_CONTROL_LOCK_PASSIVE {
                base administrative-control;
                description "The intention is for the entity to become locked but no effort is expected to move to the Locked state (the state will be achieved once all users stop using the resource). 
                    The entity may be LOCKED.";
            }
            identity ADMINISTRATIVE_CONTROL_LOCK_ACTIVE {
                base administrative-control;
                description "The intention is for the entity to become locked and it is expected that effort will be made to move to the Locked state (users will be actively removed). 
                    The entity may already be LOCKED.";
            }
            identity ADMINISTRATIVE_CONTROL_LOCK_IMMEDIATE {
                base administrative-control;
                description "The intention is for the entity to become locked and it is expected to move to the Locked state immediately (users will be force removed). 
                    The entity may already be LOCKED.";
            }
            identity ADMINISTRATIVE_CONTROL_QUIESCENT {
                base administrative-control;
                description "The administrative state is at a stable value (LOCKED/UNLOCKED) and no action is being taken.";
            }
            identity LIFECYCLE_STATE {
                description "none";
            }
            identity LIFECYCLE_STATE_PLANNED {
                base lifecycle-state;
                description "The resource is planned but is not present in the network.
                    Should include a 'time' when the resources are expected to be installed.";
            }
            identity LIFECYCLE_STATE_POTENTIAL_AVAILABLE {
                base lifecycle-state;
                description "The supporting resources are present in the network but are shared with other clients; or require further configuration before they can be used; or both.
                    (1) When a potential resource is configured and allocated to a client it is moved to the INSTALLED state for that client.
                    (2) If the potential resource has been consumed (e.g. allocated to another client) it is moved to the POTENTIAL BUSY state for all other clients.";
            }
            identity LIFECYCLE_STATE_POTENTIAL_BUSY {
                base lifecycle-state;
                description "The supporting resources are present in the network but have been allocated to other clients.";
            }
            identity LIFECYCLE_STATE_INSTALLED {
                base lifecycle-state;
                description "The resource is present in the network and is capable of providing the service.";
            }
            identity LIFECYCLE_STATE_PENDING_REMOVAL {
                base lifecycle-state;
                description "The resource has been marked for removal.  Should include a “time” when the resources are expected to be removed.";
            }
            identity BLOCK_DIRECTION {
                description "none";
            }
            identity BLOCK_DIRECTION_NO_BLOCK {
                base block-direction;
                description "none";
            }
            identity ACTION_VERBS {
                description "none";
            }
            identity ACTION_VERBS_CREATE_POST_ADD {
                base action-verbs;
                description "none";
            }
            identity ACTION_VERBS_SET_UPDATE_PUT_MODIFY_WRITE_ADD {
                base action-verbs;
                description "none";
            }
            identity ACTION_VERBS_GET_READ {
                base action-verbs;
                description "none";
            }
            identity ACTION_VERBS_DELETE_REMOVE {
                base action-verbs;
                description "none";
            }
            identity ACTIVITY_DIRECTIVE {
                description "none";
            }
            identity ACTIVITY_DIRECTIVE_STRUCTURE_IS_NOT {
                base activity-directive;
                description "none";
            }
            identity ACTIVITY_DIRECTIVE_NEW_STRUCTURE_AND_VALUES {
                base activity-directive;
                description "none";
            }
            identity ACTIVITY_DIRECTIVE_INCREMENTAL_STRUCTURE_AND_VALUES {
                base activity-directive;
                description "none";
            }
            identity ACTIVITY_DIRECTIVE_ONLY_VALUES_IN_EXISTING_STRUCTURE {
                base activity-directive;
                description "none";
            }
            identity ACTIVITY_DIRECTIVE_DEFINED_BY_VERB {
                base activity-directive;
                description "none";
            }
            identity ACTION_EFFORT {
                description "none";
            }
            identity ACTION_EFFORT_BEST_EFFORT {
                base action-effort;
                description "none";
            }
            identity ACTION_EFFORT_EXACT_MATCH {
                base action-effort;
                description "none";
            }
            identity PAUSE_RESUME_RULE {
                description "none";
            }
            identity PAUSE_RESUME_RULE_NO_PAUSE_POSSIBLE {
                base pause-resume-rule;
                description "none";
            }
            identity CONNECTOR_AND_PIN_ORIENTATION {
                description "none";
            }
            identity CONNECTOR_AND_PIN_ORIENTATION_MALE {
                base connector-and-pin-orientation;
                description "The connecting elements are dominantly protrusions.";
            }
            identity CONNECTOR_AND_PIN_ORIENTATION_FEMALE {
                base connector-and-pin-orientation;
                description "The connecting elements are dominantly indentations.";
            }
            identity CONNECTOR_AND_PIN_ORIENTATION_SYMMETRIC_NEUTRAL {
                base connector-and-pin-orientation;
                description "The pin (and housing) orientation combination is such that it is symmetric so a connector is compatible with itself.
                    The connecting element may be a surface rather than protrusions or indentations.";
            }
            identity EQUIPMENT_CATEGORY {
                description "none";
            }
            identity EQUIPMENT_CATEGORY_SUBRACK {
                base equipment-category;
                description "An assembly with holders designed to accommodate CIRCUIT_PACKs. 
                    The assembly is designed to be mounted in a RACK.";
            }
            identity EQUIPMENT_CATEGORY_CIRCUIT_PACK {
                base equipment-category;
                description "An assembly with connectors compatible with those in a holder.
                    The assembly is designed to be mounted in a holder (SLOT) of a SUBRACK.
                    May also support holders (SLOTs) for SMALL_FORMFACTOR_PLUGGABLEs.";
            }
            identity EQUIPMENT_CATEGORY_SMALL_FORMFACTOR_PLUGGABLE {
                base equipment-category;
                description "A small assembly (compared to a CIRCUIT_PACK) with connectors compatible with those in a holder.
                    The assembly is designed to be mounted in a holder (SLOT) of a CIRCUIT_PACK or STAND_ALONE_UNIT.";
            }
            identity EQUIPMENT_CATEGORY_STAND_ALONE_UNIT {
                base equipment-category;
                description "An assembly with connectors for cabling and potentially with holders.
                    The assembly is designed to be mounted in a freeform environment (on a table or simple mechanical cabinet).
                    May support holders (SLOTs) for CIRCUIT_PACKs or for SMALL_FORMFACTOR_PLUGGABLEs.";
            }
            identity EQUIPMENT_CATEGORY_RACK {
                base equipment-category;
                description "A mechanical assembly with cabling and predefined mounting points for particular SUBRACK types.
                    The assembly is designed to be mounted on the floor in a row with other RACKs.";
            }
            identity HOLDER_CATEGORY {
                description "none";
            }
            identity HOLDER_CATEGORY_SLOT {
                base holder-category;
                description "A guided holder with fixed connectors.
                    The guided holder is designed to take a particular form of CIRCUIT_PACK or SMALL_FORMFACTOR_PLUGGABLE";
            }
            identity FORWARDING_RULE {
                description "none";
            }
            identity FORWARDING_RULE_CANNOT_FORWARD_ACROSS_FD_LINK {
                base forwarding-rule;
                description "LTPs referenced by the FD (or indirectly by the Link between FDs) cannot have FCs created between them.
                    This rule overrides all others.";
            }
            identity FORWARDING_RULE_MUST_FORWARD_ACROSS_FD_LINK {
                base forwarding-rule;
                description "LTPs referenced by the FD (or indirectly by the Link between FDs) MUST have FCs created between them.
                    This rule overrides all others except the CANNOT_FORWARD rule.";
            }
            identity FORWARDING_RULE_MAY_FORWARD_ACROSS_FD_LINK {
                base forwarding-rule;
                description "LTPs referenced by the FD (or indirectly by the Link between FDs) may have FCs created between them.
                    FCs may not be created between points that are not related by this rule either directly in an FD or indirectly via a Link linking two or more FDs.
                    For a Link points in an FD at one end of the Link can be connected to points in an FD at an other end of the Link.";
            }
            identity FORWARDING_RULE_NULL_FORWARDING_RULE {
                base forwarding-rule;
                description "none";
            }
            identity RULE_TYPE {
                description "none";
            }
            identity RULE_TYPE_FORWARDING {
                base rule-type;
                description "The rule relates to creation of FCs.";
            }
            identity RULE_TYPE_COST {
                base rule-type;
                description "The rule relates to forwarding cost.";
            }
            identity RULE_TYPE_RISK {
                base rule-type;
                description "The rule relates to forwarding risk.";
            }
            identity RULE_TYPE_CAPACITY {
                base rule-type;
                description "none";
            }
            identity PORT_ROLE_RULE {
                description "none";
            }
            identity PORT_ROLE_RULE_SAME_ROLE {
                base port-role-rule;
                description "none";
            }
            identity PORT_ROLE_RULE_DIFFERENT_ROLE {
                base port-role-rule;
                description "none";
            }
            identity PORT_ROLE_RULE_ANY_ROLE {
                base port-role-rule;
                description "none";
            }
            identity SIGNAL_PROPERTY_VALUE_RULE {
                description "none";
            }
            identity SIGNAL_PROPERTY_VALUE_RULE_SAME_VALUE {
                base signal-property-value-rule;
                description "none";
            }
            identity SIGNAL_PROPERTY_VALUE_RULE_ANY_VALUE {
                base signal-property-value-rule;
                description "none";
            }
            identity TERMINATION_DIRECTION {
                description "none";
            }
            identity TERMINATION_DIRECTION_BIDIRECTIONAL {
                base termination-direction;
                description "A Termination with both SINK and SOURCE flows.";
            }
            identity TERMINATION_DIRECTION_SINK {
                base termination-direction;
                description "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity.";
            }
            identity TERMINATION_DIRECTION_SOURCE {
                base termination-direction;
                description "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity.";
            }
            identity TERMINATION_DIRECTION_UNDEFINED_OR_UNKNOWN {
                base termination-direction;
                description "Not a normal state. The system is unable to determine the correct value.";
            }
            identity TERMINATION_DIRECTION {
                description "none";
            }
            identity TERMINATION_DIRECTION_BIDIRECTIONAL {
                base termination-direction;
                description "A Termination with both SINK and SOURCE flows.";
            }
            identity TERMINATION_DIRECTION_SINK {
                base termination-direction;
                description "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base termination-direction;
                description "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base termination-direction;
                description "Not a normal state. The system is unable to determine the correct value.";
            }
            identity ACTION_VERBS {
                description "none";
            }
            identity ACTION_VERBS_CREATE_POST_ADD {
                base action-verbs;
                description "none";
            }
            identity ACTION_VERBS_SET_UPDATE_PUT_MODIFY_WRITE_ADD {
                base action-verbs;
                description "none";
            }
            identity ACTION_VERBS_GET_READ {
                base action-verbs;
                description "none";
            }
            identity ACTION_VERBS_DELETE_REMOVE {
                base action-verbs;
                description "none";
            }
            identity DIRECTION {
                description "none";
            }
            identity DIRECTION_IN {
                base direction;
                description "none";
            }
            identity DIRECTION_OUT {
                base direction;
                description "none";
            }
            identity DIRECTION_BIDIRECTIONAL {
                base direction;
                description "none";
            }
            typedef date-and-time {
                type string;
                description "This primitive type defines the date and time according to the following structure:
                    'yyyyMMddhhmmss.s[Z|{+|-}HHMm]' where:
                    yyyy    '0000'..'9999'    year
                    MM        '01'..'12'            month
                    dd        '01'..'31'            day
                    hh        '00'..'23'            hour
                    mm        '00'..'59'            minute
                    ss        '00'..'59'            second
                    s        '.0'..'.9'            tenth of second (set to '.0' if EMS or NE cannot support this granularity)
                    Z        'Z'                    indicates UTC (rather than local time)
                    {+|-}    '+' or '-'            delta from UTC
                    HH        '00'..'23'            time zone difference in hours
                    Mm        '00'..'59'            time zone difference in minutes.";
            }
            typedef bit-string {
                type string;
                description "This primitive type defines a bit oriented string.
                    The size of the BitString will be defined in the valueRange property of the attribute; according to ASN.1 (X.680).
                    The semantic of each bit position will be defined in the Documentation field of the attribute.";
            }
            typedef printable-string {
                type string;
                description "A string that only includes printable characters.";
            }
            typedef to-be-defined {
                type string;
                description "This type is used when the actual type of the attribute is expected to be complex but where the type has not yet been developed. 
                    This type should only be used for attributes that are experimental.";
            }

        /***********************
        * package super-classes-and-common-packages
        **********************/ 
            /***********************
            * package object-classes
            **********************/ 
                grouping name {
                    list name {
                        min-elements 1;
                        uses name-and-value;
                        description "List of names.";
                    }
                    description "Name: A property of an entity with a value that is unique in some namespace but may change during the life of the entity. A name carries no semantics with respect to the purpose of the entity.";
                }
                grouping global-class {
                    list local-id {
                        uses name-and-value;
                        description "An identifier that is unique in the context of some scope that is less than the global scope.
                            (This should be considered in the context of Identifier: A property of an entity/role with a value that is unique within an identifier space, where the identifier space is itself unique, and immutable. The identifier therefore represents the identity of the entity/role. An identifier carries no semantics with respect to the purpose of the entity.)";
                    }
                    leaf uuid {
                        type universal-id;
                        description "UUID: An identifier that is universally unique
                            (This should be considered in the context of Identifier: A property of an entity/role with a value that is unique within an identifier space, where the identifier space is itself globally unique, and immutable. An identifier carries no semantics with respect to the purpose or state of the entity)
                            The uuid should be treated as opaque by the user.";
                    }
                    uses name;
                    uses label;
                    uses extension;
                    uses state-pac;
                    uses address;
                    description "Represents a type of thing (an Entity) that has instances which can exist in their own right (independently of any others).
                        Entity: Has identity, defined boundary, properties, functionality and lifecycle in a global context.
                        (This should be considered in the context of a Class: (usage) The representation of a thing that may be an entity or an inseparable Entity Feature).";
                }
                grouping local-class {
                    list local-id {
                        min-elements 1;
                        uses name-and-value;
                        description "An identifier that is unique in the context of some scope that is less than the global scope.
                            (This should be considered in the context of Identifier: A property of an entity/role with a value that is unique within an identifier space, where the identifier space is itself unique, and immutable. The identifier therefore represents the identity of the entity/role. An identifier carries no semantics with respect to the purpose of the entity.)";
                    }
                    uses name;
                    uses label;
                    uses extension;
                    uses state-pac;
                    uses address;
                    description "A LocalClass represents a Feature of an Entity. It is inseparable from a GlobalClass but is a distinct feature of that GlobalClass such that the instances of LocalClass are able to have associations to other instances.
                        Feature of an Entity: An inseparable, externally distinguishable part of an entity.
                        The mandatory LocalId of the LocalClass instance is unique in the context of the GlobalClass from which it is inseparable.
                        (This should be considered in the context of a Class: (usage) The representation of a thing that may be an entity or an inseparable feature of an entity.)
                        ";
                }
                grouping label {
                    list label {
                        uses name-and-value;
                        description "List of labels.";
                    }
                    description "A property of an entity with a value that is not expected to be unique and is allowed to change. A label carries no semantics with respect to the purpose of the entity and has no effect on the entity behavior or state.";
                }
                grouping extension {
                    list extension {
                        uses name-and-value;
                        description "List of simple name-value extensions.";
                    }
                    description "Extension provides an opportunity to define properties not declared in the class that extend the class enabling a realization with simple ad-hoc extension of standard classes to be conformant.";
                }
                grouping universal-id-authority {
                    leaf uuid {
                        type universal-id;
                        description "The UUID for the UUID authority.";
                    }
                    description "Represents the authority that controls the allocation of UUIDs.";
                }
                grouping name-and-value-authority {
                    leaf uuid {
                        type universal-id;
                        description "The UUID for the NameAndValueAuthority.";
                    }
                    description "Represents the authority that controls the legal values for the names and values of a name/value attribute.";
                }
                grouping conditional-package {
                    uses extension;
                    uses label;
                    description "The base class for conditional packages.";
                }
                grouping address {
                    list address {
                        uses address;
                        description "One or more descriptions of the location.";
                    }
                    description "Provides an opportunity to state the location of the entity via one or more hierarchies of narrowing contexts.";
                }

            /***********************
            * package type-definitions
            **********************/ 
                identity PORT_DIRECTION {
                    description "none";
                }
                identity PORT_DIRECTION_BIDIRECTIONAL {
                    base port-direction;
                    description "The Port has both an INPUT flow and an OUTPUT flow defined.";
                }
                identity PORT_DIRECTION_INPUT {
                    base port-direction;
                    description "The Port only has definition for a flow into the Forwarding entity (i.e. an ingress flow).";
                }
                identity PORT_DIRECTION_OUTPUT {
                    base port-direction;
                    description "The Port only has definition for a flow out of the Forwarding entity (i.e. an egress flow).";
                }
                identity PORT_DIRECTION_UNIDENTIFIED_OR_UNKNOWN {
                    base port-direction;
                    description "Not a normal state. The system is unable to determine the correct value.";
                }
                identity PORT_DIRECTION_OMNIDIRECTIONAL {
                    base port-direction;
                    description "none";
                }
                identity FORWARDING_DIRECTION {
                    description "none";
                }
                identity FORWARDING_DIRECTION_BIDIRECTIONAL {
                    base forwarding-direction;
                    description "The Forwarding entity supports both BIDIRECTIONAL flows at all Ports (i.e. all Ports have both an INPUT flow and an OUTPUT flow defined).";
                }
                identity FORWARDING_DIRECTION_UNIDIRECTIONAL {
                    base forwarding-direction;
                    description "The Forwarding entity has Ports that are either INPUT or OUTPUT. It has no BIDIRECTIONAL Ports.";
                }
                identity FORWARDING_DIRECTION_UNDEFINED_OR_UNKNOWN {
                    base forwarding-direction;
                    description "Not a normal state. The system is unable to determine the correct value.";
                }
                identity FORWARDING_DIRECTION_OMNIDIRECTIONAL {
                    base forwarding-direction;
                    description "none";
                }
                identity TERMINATION_DIRECTION {
                    description "none";
                }
                identity TERMINATION_DIRECTION_BIDIRECTIONAL {
                    base termination-direction;
                    description "A Termination with both SINK and SOURCE flows.";
                }
                identity TERMINATION_DIRECTION_SINK {
                    base termination-direction;
                    description "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base termination-direction;
                    description "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base termination-direction;
                    description "Not a normal state. The system is unable to determine the correct value.";
                }
                identity EXTENDED_TERMINATION_DIRECTION {
                    description "none";
                }
                identity EXTENDED_TERMINATION_DIRECTION_CONTRA_DIRECTION_SINK {
                    base extended-termination-direction;
                    description "The essential flow of the Termination entity is SINK (i.e. up the layer stack) but the INPUT flow of the Termination entity was provided by a SOURCE OUTPUT or taken from a SOURCE INPUT (duplicating the input signal) hence reversing the flow orientation from down the layer stack to up the layer stack.";
                }
                identity EXTENDED_TERMINATION_DIRECTION_CONTRA_DIRECTION_SOURCE {
                    base extended-termination-direction;
                    description "The essential flow of the Termination entity is SOURCE (i.e. down the layer stack) but the OUTPUT flow of the Termination entity was fed to (and replaces) a SINK OUTPUT or was fed to a SINK INPUT (replacing the normal flow) hence reversing the flow orientation from down the layer stack to up the layer stack.";
                }
                identity TERMINATION_STATE {
                    description "none";
                }
                identity TERMINATION_STATE_LP_CAN_NEVER_TERMINATE {
                    base termination-state;
                    description "A non-flexible case that can never be terminated.";
                }
                identity TERMINATION_STATE_LP_NOT_TERMINATED {
                    base termination-state;
                    description "A flexible termination that can terminate but is currently not terminated.";
                }
                identity TERMINATION_STATE_TERMINATED_SERVER_TO_CLIENT_FLOW {
                    base termination-state;
                    description "A flexible termination that is currently terminated for server to client flow only.";
                }
                identity TERMINATION_STATE_TERMINATED_CLIENT_TO_SERVER_FLOW {
                    base termination-state;
                    description "A flexible termination that is currently terminated for client to server flow only.";
                }
                identity TERMINATION_STATE_TERMINATED_BIDIRECTIONAL {
                    base termination-state;
                    description "A flexible termination that is currently terminated in both directions of flow.";
                }
                identity TERMINATION_STATE_LP_PERMENANTLY_TERMINATED {
                    base termination-state;
                    description "A non-flexible termination that is always terminated (in both directions of flow for a bidirectional case and in the one direction of flow for both unidirectional cases).";
                }
                identity TERMINATION_STATE_TERMINATION_STATE_UNKNOWN {
                    base termination-state;
                    description "There TerminationState cannot be determined.";
                }
                identity PROTECTION_REASON {
                    description "none";
                }
                identity PROTECTION_REASON_WAIT_TO_REVERT {
                    base protection-reason;
                    description "The resource is selected as control is waiting to restore to a preferred resource.";
                }
                identity PROTECTION_REASON_SIGNAL_DEGRADE {
                    base protection-reason;
                    description "The resource is selected as the best preferred resource is in signal degrade.";
                }
                identity PROTECTION_REASON_SIGNAL_FAIL {
                    base protection-reason;
                    description "The resource is selected as the best preferred resource is in signal fail.";
                }
                identity ROUTE_SELECTION_CONTROL {
                    description "none";
                }
                identity ROUTE_SELECTION_CONTROL_LOCK_OUT {
                    base route-selection-control;
                    description "The resource is configured to temporarily not be available for use in the protection scheme(s) it is part of.
                        This overrides all other protection control states including forced.
                        If the item is locked out, then it cannot be used under any circumstances.
                        Note: Only relevant when part of a protection scheme.
                        Note: if a protection process that has a relationship to the item (i.e. is one of the options the protection process may choose) is deactivated by being isFrozen = true) then the lockout request will be rejected. ";
                }
                identity ROUTE_SELECTION_REASON {
                    description "none";
                }
                identity SWITCH_CONTROL {
                    description "none";
                }
                identity SWITCH_CONTROL_NORMAL {
                    base switch-control;
                    description "No administrative control applied to the switch.";
                }
                identity SWITCH_CONTROL_MANUAL {
                    base switch-control;
                    description "Resource temporarily chosen by control configuration where the resource is not the preferred resource.
                        Preferred resource has highest priority.
                        Temporarily overrides reversion.
                        If this resource fails, it will switch to best available resource. 
                        If resource selected is shared and another FC requires the resource, then the selection control will change to Normal and switch to best available based upon normal rules.
                        Cannot manually switch a Forced switch, cannot remove a forced switch, cannot switch to a locked out item and will be rejected if the protection process is deactivated by being Freeze = true).
                        A manual switch/route that is selecting an FcPort, LTP, FC, Link or Route that is subsequently set to LOCK_OUT will have the manual removed (changed to NORMAL) and will switch away from the  FcPort with LOCK_OUT to best available based upon normal rules.
                        A manual switch that is selecting an FcPort that is subsequently selected by a Forced switch will be restored to normal operation and the manual will be removed.
                        A manual switch/route that is selecting an FcPort, LTP, FC, Link or Route that is subsequently manual selected by another switch/route  will have the manual removed and will switch away from the FcPort.
                        Can be returned to NORMAL by configuration action.";
                }
                identity SWITCH_CONTROL_FORCED {
                    base switch-control;
                    description "Resource temporarily chosen by control configuration where the resource is not the preferred resource.
                        Preferred resource has highest priority.
                        Temporarily overrides reversion.
                        If this resource fails it will NOT switch. 
                        If resource selected is shared and another FC requires the resource through a FORCE on that FC and the FC is of a higher FcPriority then the selection control on this FC will change to NORMAL and switch to best available based upon normal rules.
                        If the resource selected is then set to LOCK_OUT then the selection control will change to NORMAL and switch to best available based upon normal rules.
                        Can be returned to NORMAL by configuration action.";
                }
                identity SWITCH_STATE_REASON {
                    description "none";
                }
                identity REVERSION_MODE {
                    description "none";
                }
                identity REVERSION_MODE_REVERTIVE {
                    base reversion-mode;
                    description "An FC switched to a lower priority (non-preferred) resource will revert to a higher priority (preferred) resource when that recovers (potentially after some hold-off time).";
                }
                identity REVERSION_MODE_NON-REVERTIVE {
                    base reversion-mode;
                    description "An FC switched to a lower priority (non-preferred) resource will not revert to a higher priority (preferred) resource when that recovers.";
                }
                identity RESILIENCE_CONTROL {
                    description "none";
                }
                identity RESILIENCE_CONTROL_QUIESCENT {
                    base resilience-control;
                    description "none";
                }
                identity RESILIENCE_CONTROL_RESTORING {
                    base resilience-control;
                    description "none";
                }
                identity RESILIENCE_CONTROL_RECOVERY_FAILED {
                    base resilience-control;
                    description "none";
                }
                identity RESILIENCE_CONTROL_UNKNOWN {
                    base resilience-control;
                    description "none";
                }
                identity RUN_MODE {
                    description "none";
                }
                identity RUN_MODE_FREE_RUN {
                    base run-mode;
                    description "The ckock is not synchronized to another clock.";
                }
                identity RUN_MODE_LOCKED {
                    base run-mode;
                    description "The clock is synchronised to another clock.";
                }
                identity RUN_MODE_HOLD_OVER {
                    base run-mode;
                    description "The clock was previously synchonised to another clock but that timing input has been lost.
                        The clock is set to the last known synchronization.";
                }
                identity OPERATIONAL_STATE {
                    description "none";
                }
                identity OPERATIONAL_STATE_DISABLED {
                    base operational-state;
                    description "The resource is unable to meet the SLA of the user of the resource. 
                        If no (explicit) SLA is defined the resource is disabled if it is totally inoperable and unable to provide service to the user.";
                }
                identity OPERATIONAL_STATE_ENABLED {
                    base operational-state;
                    description "The resource is partially or fully operable and available for use.";
                }
                identity ADMINISTRATIVE_STATE {
                    description "none";
                }
                identity ADMINISTRATIVE_STATE_LOCKED {
                    base administrative-state;
                    description "Users are administratively prohibited from making use of the resource.";
                }
                identity ADMINISTRATIVE_STATE_UNLOCKED {
                    base administrative-state;
                    description "Users are allowed to use the resource.";
                }
                identity ADMINISTRATIVE_STATE_SHUTTING_DOWN {
                    base administrative-state;
                    description "The entity is administratively restricted to existing instances of use only. There may be specific actions to remove existing uses. No new instances of use can be enabled.
                        The resource automatically transitions to “locked” when the last user quits. 
                        The administrative state is not visible in the client context. 
                        The lifecycle state “pending removal” should be used to indicate to the client that the provider intends to remove the resource.";
                }
                identity ADMINISTRATIVE_CONTROL {
                    description "none";
                }
                identity ADMINISTRATIVE_CONTROL_UNLOCK {
                    base administrative-control;
                    description "The intention is for the entity to become unlocked.
                        The entity may already be UNLOCKED.";
                }
                identity ADMINISTRATIVE_CONTROL_LOCK_PASSIVE {
                    base administrative-control;
                    description "The intention is for the entity to become locked but no effort is expected to move to the Locked state (the state will be achieved once all users stop using the resource). 
                        The entity may be LOCKED.";
                }
                identity ADMINISTRATIVE_CONTROL_LOCK_ACTIVE {
                    base administrative-control;
                    description "The intention is for the entity to become locked and it is expected that effort will be made to move to the Locked state (users will be actively removed). 
                        The entity may already be LOCKED.";
                }
                identity ADMINISTRATIVE_CONTROL_LOCK_IMMEDIATE {
                    base administrative-control;
                    description "The intention is for the entity to become locked and it is expected to move to the Locked state immediately (users will be force removed). 
                        The entity may already be LOCKED.";
                }
                identity ADMINISTRATIVE_CONTROL_QUIESCENT {
                    base administrative-control;
                    description "The administrative state is at a stable value (LOCKED/UNLOCKED) and no action is being taken.";
                }
                identity LIFECYCLE_STATE {
                    description "none";
                }
                identity LIFECYCLE_STATE_PLANNED {
                    base lifecycle-state;
                    description "The resource is planned but is not present in the network.
                        Should include a 'time' when the resources are expected to be installed.";
                }
                identity LIFECYCLE_STATE_POTENTIAL_AVAILABLE {
                    base lifecycle-state;
                    description "The supporting resources are present in the network but are shared with other clients; or require further configuration before they can be used; or both.
                        (1) When a potential resource is configured and allocated to a client it is moved to the INSTALLED state for that client.
                        (2) If the potential resource has been consumed (e.g. allocated to another client) it is moved to the POTENTIAL BUSY state for all other clients.";
                }
                identity LIFECYCLE_STATE_POTENTIAL_BUSY {
                    base lifecycle-state;
                    description "The supporting resources are present in the network but have been allocated to other clients.";
                }
                identity LIFECYCLE_STATE_INSTALLED {
                    base lifecycle-state;
                    description "The resource is present in the network and is capable of providing the service.";
                }
                identity LIFECYCLE_STATE_PENDING_REMOVAL {
                    base lifecycle-state;
                    description "The resource has been marked for removal.  Should include a “time” when the resources are expected to be removed.";
                }
                identity BLOCK_DIRECTION {
                    description "none";
                }
                identity BLOCK_DIRECTION_NO_BLOCK {
                    base block-direction;
                    description "none";
                }
                identity ACTION_VERBS {
                    description "none";
                }
                identity ACTION_VERBS_CREATE_POST_ADD {
                    base action-verbs;
                    description "none";
                }
                identity ACTION_VERBS_SET_UPDATE_PUT_MODIFY_WRITE_ADD {
                    base action-verbs;
                    description "none";
                }
                identity ACTION_VERBS_GET_READ {
                    base action-verbs;
                    description "none";
                }
                identity ACTION_VERBS_DELETE_REMOVE {
                    base action-verbs;
                    description "none";
                }
                identity ACTIVITY_DIRECTIVE {
                    description "none";
                }
                identity ACTIVITY_DIRECTIVE_STRUCTURE_IS_NOT {
                    base activity-directive;
                    description "none";
                }
                identity ACTIVITY_DIRECTIVE_NEW_STRUCTURE_AND_VALUES {
                    base activity-directive;
                    description "none";
                }
                identity ACTIVITY_DIRECTIVE_INCREMENTAL_STRUCTURE_AND_VALUES {
                    base activity-directive;
                    description "none";
                }
                identity ACTIVITY_DIRECTIVE_ONLY_VALUES_IN_EXISTING_STRUCTURE {
                    base activity-directive;
                    description "none";
                }
                identity ACTIVITY_DIRECTIVE_DEFINED_BY_VERB {
                    base activity-directive;
                    description "none";
                }
                identity ACTION_EFFORT {
                    description "none";
                }
                identity ACTION_EFFORT_BEST_EFFORT {
                    base action-effort;
                    description "none";
                }
                identity ACTION_EFFORT_EXACT_MATCH {
                    base action-effort;
                    description "none";
                }
                identity PAUSE_RESUME_RULE {
                    description "none";
                }
                identity PAUSE_RESUME_RULE_NO_PAUSE_POSSIBLE {
                    base pause-resume-rule;
                    description "none";
                }
                identity CONNECTOR_AND_PIN_ORIENTATION {
                    description "none";
                }
                identity CONNECTOR_AND_PIN_ORIENTATION_MALE {
                    base connector-and-pin-orientation;
                    description "The connecting elements are dominantly protrusions.";
                }
                identity CONNECTOR_AND_PIN_ORIENTATION_FEMALE {
                    base connector-and-pin-orientation;
                    description "The connecting elements are dominantly indentations.";
                }
                identity CONNECTOR_AND_PIN_ORIENTATION_SYMMETRIC_NEUTRAL {
                    base connector-and-pin-orientation;
                    description "The pin (and housing) orientation combination is such that it is symmetric so a connector is compatible with itself.
                        The connecting element may be a surface rather than protrusions or indentations.";
                }
                identity EQUIPMENT_CATEGORY {
                    description "none";
                }
                identity EQUIPMENT_CATEGORY_SUBRACK {
                    base equipment-category;
                    description "An assembly with holders designed to accommodate CIRCUIT_PACKs. 
                        The assembly is designed to be mounted in a RACK.";
                }
                identity EQUIPMENT_CATEGORY_CIRCUIT_PACK {
                    base equipment-category;
                    description "An assembly with connectors compatible with those in a holder.
                        The assembly is designed to be mounted in a holder (SLOT) of a SUBRACK.
                        May also support holders (SLOTs) for SMALL_FORMFACTOR_PLUGGABLEs.";
                }
                identity EQUIPMENT_CATEGORY_SMALL_FORMFACTOR_PLUGGABLE {
                    base equipment-category;
                    description "A small assembly (compared to a CIRCUIT_PACK) with connectors compatible with those in a holder.
                        The assembly is designed to be mounted in a holder (SLOT) of a CIRCUIT_PACK or STAND_ALONE_UNIT.";
                }
                identity EQUIPMENT_CATEGORY_STAND_ALONE_UNIT {
                    base equipment-category;
                    description "An assembly with connectors for cabling and potentially with holders.
                        The assembly is designed to be mounted in a freeform environment (on a table or simple mechanical cabinet).
                        May support holders (SLOTs) for CIRCUIT_PACKs or for SMALL_FORMFACTOR_PLUGGABLEs.";
                }
                identity EQUIPMENT_CATEGORY_RACK {
                    base equipment-category;
                    description "A mechanical assembly with cabling and predefined mounting points for particular SUBRACK types.
                        The assembly is designed to be mounted on the floor in a row with other RACKs.";
                }
                identity HOLDER_CATEGORY {
                    description "none";
                }
                identity HOLDER_CATEGORY_SLOT {
                    base holder-category;
                    description "A guided holder with fixed connectors.
                        The guided holder is designed to take a particular form of CIRCUIT_PACK or SMALL_FORMFACTOR_PLUGGABLE";
                }
                identity FORWARDING_RULE {
                    description "none";
                }
                identity FORWARDING_RULE_CANNOT_FORWARD_ACROSS_FD_LINK {
                    base forwarding-rule;
                    description "LTPs referenced by the FD (or indirectly by the Link between FDs) cannot have FCs created between them.
                        This rule overrides all others.";
                }
                identity FORWARDING_RULE_MUST_FORWARD_ACROSS_FD_LINK {
                    base forwarding-rule;
                    description "LTPs referenced by the FD (or indirectly by the Link between FDs) MUST have FCs created between them.
                        This rule overrides all others except the CANNOT_FORWARD rule.";
                }
                identity FORWARDING_RULE_MAY_FORWARD_ACROSS_FD_LINK {
                    base forwarding-rule;
                    description "LTPs referenced by the FD (or indirectly by the Link between FDs) may have FCs created between them.
                        FCs may not be created between points that are not related by this rule either directly in an FD or indirectly via a Link linking two or more FDs.
                        For a Link points in an FD at one end of the Link can be connected to points in an FD at an other end of the Link.";
                }
                identity FORWARDING_RULE_NULL_FORWARDING_RULE {
                    base forwarding-rule;
                    description "none";
                }
                identity RULE_TYPE {
                    description "none";
                }
                identity RULE_TYPE_FORWARDING {
                    base rule-type;
                    description "The rule relates to creation of FCs.";
                }
                identity RULE_TYPE_COST {
                    base rule-type;
                    description "The rule relates to forwarding cost.";
                }
                identity RULE_TYPE_RISK {
                    base rule-type;
                    description "The rule relates to forwarding risk.";
                }
                identity RULE_TYPE_CAPACITY {
                    base rule-type;
                    description "none";
                }
                identity PORT_ROLE_RULE {
                    description "none";
                }
                identity PORT_ROLE_RULE_SAME_ROLE {
                    base port-role-rule;
                    description "none";
                }
                identity PORT_ROLE_RULE_DIFFERENT_ROLE {
                    base port-role-rule;
                    description "none";
                }
                identity PORT_ROLE_RULE_ANY_ROLE {
                    base port-role-rule;
                    description "none";
                }
                identity SIGNAL_PROPERTY_VALUE_RULE {
                    description "none";
                }
                identity SIGNAL_PROPERTY_VALUE_RULE_SAME_VALUE {
                    base signal-property-value-rule;
                    description "none";
                }
                identity SIGNAL_PROPERTY_VALUE_RULE_ANY_VALUE {
                    base signal-property-value-rule;
                    description "none";
                }
                identity TERMINATION_DIRECTION {
                    description "none";
                }
                identity TERMINATION_DIRECTION_BIDIRECTIONAL {
                    base termination-direction;
                    description "A Termination with both SINK and SOURCE flows.";
                }
                identity TERMINATION_DIRECTION_SINK {
                    base termination-direction;
                    description "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity.";
                }
                identity TERMINATION_DIRECTION_SOURCE {
                    base termination-direction;
                    description "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity.";
                }
                identity TERMINATION_DIRECTION_UNDEFINED_OR_UNKNOWN {
                    base termination-direction;
                    description "Not a normal state. The system is unable to determine the correct value.";
                }
                identity TERMINATION_DIRECTION {
                    description "none";
                }
                identity TERMINATION_DIRECTION_BIDIRECTIONAL {
                    base termination-direction;
                    description "A Termination with both SINK and SOURCE flows.";
                }
                identity TERMINATION_DIRECTION_SINK {
                    base termination-direction;
                    description "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base termination-direction;
                    description "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base termination-direction;
                    description "Not a normal state. The system is unable to determine the correct value.";
                }
                identity ACTION_VERBS {
                    description "none";
                }
                identity ACTION_VERBS_CREATE_POST_ADD {
                    base action-verbs;
                    description "none";
                }
                identity ACTION_VERBS_SET_UPDATE_PUT_MODIFY_WRITE_ADD {
                    base action-verbs;
                    description "none";
                }
                identity ACTION_VERBS_GET_READ {
                    base action-verbs;
                    description "none";
                }
                identity ACTION_VERBS_DELETE_REMOVE {
                    base action-verbs;
                    description "none";
                }
                identity DIRECTION {
                    description "none";
                }
                identity DIRECTION_IN {
                    base direction;
                    description "none";
                }
                identity DIRECTION_OUT {
                    base direction;
                    description "none";
                }
                identity DIRECTION_BIDIRECTIONAL {
                    base direction;
                    description "none";
                }
                grouping name-and-value {
                    leaf value-name {
                        type string;
                        description "The name of the value. The value need not have a name.";
                    }
                    leaf value {
                        type string;
                        description "The value.";
                    }
                    leaf name-and-value-authority {
                        type leafref {
                            path '/core-model:name-and-value-authority/core-model:';
                        }
                        description "The authority that defines the named value.";
                    }
                    leaf global-class {
                        type leafref {
                            path '/core-model:global-class/core-model:';
                        }
                        description "The scope of the name uniqueness.";
                    }
                    leaf local-class {
                        type leafref {
                            path '/core-model:local-class/core-model:';
                        }
                        description "The scope of the name uniqueness.";
                    }
                    description "A scoped name-value pair.";
                }
                typedef universal-id {
                    type string;
                    description "The universal ID value where the mechanism for generation is defined by some authority not directly referenced in the structure.
                        An example structure is [IETF RFC4122].";
                }
                grouping address {
                    leaf address-name {
                        type string;
                        description "The name of the address (to allow the specific hierarchy to be distinguished from others for the same entity).";
                    }
                    list address-element {
                        uses address-element;
                        description "The elements of the address that form the recursive scope narrowing.";
                    }
                    description "A description of location via a hierarchy of narrowing contexts.";
                }
                grouping local-id-and-class {
                    leaf class-of-instance {
                        type string;
                        description "The class to which the name refers.";
                    }
                    container local-id {
                        uses name-and-value;
                        description "The localId of the entity.";
                    }
                    description "The localId and the class of entity that it identifies.";
                }
                grouping name-and-class {
                    leaf class-of-instance {
                        type string;
                        description "The class to which the name refers.";
                    }
                    container name {
                        uses name-and-value;
                        description "If the element is a name.";
                    }
                    description "The name and the class of entity that it names.";
                }
                grouping address-element {
                    leaf address-element-name {
                        type string;
                        description "The name of the address element (e.g. 'shelf' as an element of a shelf/slot/port addressing scheme).
                            The remainder of the structure has the reference for the shelf.
                            ";
                    }
                    container local-id {
                        uses local-id-and-class;
                        description "If the element is a localId (where the element above in the hierarchy must be the context in which the specific localId is relevant).";
                    }
                    leaf uuid {
                        type universal-id;
                        description "If the element is a uuid (where this element could be the top of a hierarchy but may also be at some level in the hierarchy where address navigation is considered necessary to assist in location of the UUID).";
                    }
                    container name {
                        uses name-and-class;
                        description "If the element is a name.";
                    }
                    container address {
                        uses address;
                        description "none";
                    }
                    leaf arbitrary-element {
                        type string;
                        description "Where the element is from some external model that is not formally represented in this model.";
                    }
                    description "One element of a hierarchy of elements.
                        Note that the element must have one and only one value chosen from a list of potential value types.";
                }


        /***********************
        * package state-model
        **********************/ 
            /***********************
            * package object-classes
            **********************/ 
                grouping state-pac {
                    leaf operational-state {
                        type operational-state;
                        config false;
                        description "The operational state is used to indicate whether or not the resource is installed and working.";
                    }
                    leaf administrative-control {
                        type administrative-control;
                        description "The administrativeControl state provides control of the availability of specific resources without modification to the provisioning of those resources.
                            The value is the current control target. The actual administrativeState may or may not be at target.";
                    }
                    leaf administrative-state {
                        type administrative-state;
                        config false;
                        description "Shows whether or not the client has permission to use or has a prohibition against using the resource.
                            The administrative state expresses usage permissions for specific resources without modification to the provisioning of those resources.";
                    }
                    leaf lifecycle-state {
                        type lifecycle-state;
                        description "Used to track the planned deployment, allocation to clients and withdrawal of resources.";
                    }
                    description "Provides general state attributes.";
                }

            /***********************
            * package type-definitions
            **********************/ 
                identity PORT_DIRECTION {
                    description "none";
                }
                identity PORT_DIRECTION_BIDIRECTIONAL {
                    base port-direction;
                    description "The Port has both an INPUT flow and an OUTPUT flow defined.";
                }
                identity PORT_DIRECTION_INPUT {
                    base port-direction;
                    description "The Port only has definition for a flow into the Forwarding entity (i.e. an ingress flow).";
                }
                identity PORT_DIRECTION_OUTPUT {
                    base port-direction;
                    description "The Port only has definition for a flow out of the Forwarding entity (i.e. an egress flow).";
                }
                identity PORT_DIRECTION_UNIDENTIFIED_OR_UNKNOWN {
                    base port-direction;
                    description "Not a normal state. The system is unable to determine the correct value.";
                }
                identity PORT_DIRECTION_OMNIDIRECTIONAL {
                    base port-direction;
                    description "none";
                }
                identity FORWARDING_DIRECTION {
                    description "none";
                }
                identity FORWARDING_DIRECTION_BIDIRECTIONAL {
                    base forwarding-direction;
                    description "The Forwarding entity supports both BIDIRECTIONAL flows at all Ports (i.e. all Ports have both an INPUT flow and an OUTPUT flow defined).";
                }
                identity FORWARDING_DIRECTION_UNIDIRECTIONAL {
                    base forwarding-direction;
                    description "The Forwarding entity has Ports that are either INPUT or OUTPUT. It has no BIDIRECTIONAL Ports.";
                }
                identity FORWARDING_DIRECTION_UNDEFINED_OR_UNKNOWN {
                    base forwarding-direction;
                    description "Not a normal state. The system is unable to determine the correct value.";
                }
                identity FORWARDING_DIRECTION_OMNIDIRECTIONAL {
                    base forwarding-direction;
                    description "none";
                }
                identity TERMINATION_DIRECTION {
                    description "none";
                }
                identity TERMINATION_DIRECTION_BIDIRECTIONAL {
                    base termination-direction;
                    description "A Termination with both SINK and SOURCE flows.";
                }
                identity TERMINATION_DIRECTION_SINK {
                    base termination-direction;
                    description "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base termination-direction;
                    description "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base termination-direction;
                    description "Not a normal state. The system is unable to determine the correct value.";
                }
                identity EXTENDED_TERMINATION_DIRECTION {
                    description "none";
                }
                identity EXTENDED_TERMINATION_DIRECTION_CONTRA_DIRECTION_SINK {
                    base extended-termination-direction;
                    description "The essential flow of the Termination entity is SINK (i.e. up the layer stack) but the INPUT flow of the Termination entity was provided by a SOURCE OUTPUT or taken from a SOURCE INPUT (duplicating the input signal) hence reversing the flow orientation from down the layer stack to up the layer stack.";
                }
                identity EXTENDED_TERMINATION_DIRECTION_CONTRA_DIRECTION_SOURCE {
                    base extended-termination-direction;
                    description "The essential flow of the Termination entity is SOURCE (i.e. down the layer stack) but the OUTPUT flow of the Termination entity was fed to (and replaces) a SINK OUTPUT or was fed to a SINK INPUT (replacing the normal flow) hence reversing the flow orientation from down the layer stack to up the layer stack.";
                }
                identity TERMINATION_STATE {
                    description "none";
                }
                identity TERMINATION_STATE_LP_CAN_NEVER_TERMINATE {
                    base termination-state;
                    description "A non-flexible case that can never be terminated.";
                }
                identity TERMINATION_STATE_LP_NOT_TERMINATED {
                    base termination-state;
                    description "A flexible termination that can terminate but is currently not terminated.";
                }
                identity TERMINATION_STATE_TERMINATED_SERVER_TO_CLIENT_FLOW {
                    base termination-state;
                    description "A flexible termination that is currently terminated for server to client flow only.";
                }
                identity TERMINATION_STATE_TERMINATED_CLIENT_TO_SERVER_FLOW {
                    base termination-state;
                    description "A flexible termination that is currently terminated for client to server flow only.";
                }
                identity TERMINATION_STATE_TERMINATED_BIDIRECTIONAL {
                    base termination-state;
                    description "A flexible termination that is currently terminated in both directions of flow.";
                }
                identity TERMINATION_STATE_LP_PERMENANTLY_TERMINATED {
                    base termination-state;
                    description "A non-flexible termination that is always terminated (in both directions of flow for a bidirectional case and in the one direction of flow for both unidirectional cases).";
                }
                identity TERMINATION_STATE_TERMINATION_STATE_UNKNOWN {
                    base termination-state;
                    description "There TerminationState cannot be determined.";
                }
                identity PROTECTION_REASON {
                    description "none";
                }
                identity PROTECTION_REASON_WAIT_TO_REVERT {
                    base protection-reason;
                    description "The resource is selected as control is waiting to restore to a preferred resource.";
                }
                identity PROTECTION_REASON_SIGNAL_DEGRADE {
                    base protection-reason;
                    description "The resource is selected as the best preferred resource is in signal degrade.";
                }
                identity PROTECTION_REASON_SIGNAL_FAIL {
                    base protection-reason;
                    description "The resource is selected as the best preferred resource is in signal fail.";
                }
                identity ROUTE_SELECTION_CONTROL {
                    description "none";
                }
                identity ROUTE_SELECTION_CONTROL_LOCK_OUT {
                    base route-selection-control;
                    description "The resource is configured to temporarily not be available for use in the protection scheme(s) it is part of.
                        This overrides all other protection control states including forced.
                        If the item is locked out, then it cannot be used under any circumstances.
                        Note: Only relevant when part of a protection scheme.
                        Note: if a protection process that has a relationship to the item (i.e. is one of the options the protection process may choose) is deactivated by being isFrozen = true) then the lockout request will be rejected. ";
                }
                identity ROUTE_SELECTION_REASON {
                    description "none";
                }
                identity SWITCH_CONTROL {
                    description "none";
                }
                identity SWITCH_CONTROL_NORMAL {
                    base switch-control;
                    description "No administrative control applied to the switch.";
                }
                identity SWITCH_CONTROL_MANUAL {
                    base switch-control;
                    description "Resource temporarily chosen by control configuration where the resource is not the preferred resource.
                        Preferred resource has highest priority.
                        Temporarily overrides reversion.
                        If this resource fails, it will switch to best available resource. 
                        If resource selected is shared and another FC requires the resource, then the selection control will change to Normal and switch to best available based upon normal rules.
                        Cannot manually switch a Forced switch, cannot remove a forced switch, cannot switch to a locked out item and will be rejected if the protection process is deactivated by being Freeze = true).
                        A manual switch/route that is selecting an FcPort, LTP, FC, Link or Route that is subsequently set to LOCK_OUT will have the manual removed (changed to NORMAL) and will switch away from the  FcPort with LOCK_OUT to best available based upon normal rules.
                        A manual switch that is selecting an FcPort that is subsequently selected by a Forced switch will be restored to normal operation and the manual will be removed.
                        A manual switch/route that is selecting an FcPort, LTP, FC, Link or Route that is subsequently manual selected by another switch/route  will have the manual removed and will switch away from the FcPort.
                        Can be returned to NORMAL by configuration action.";
                }
                identity SWITCH_CONTROL_FORCED {
                    base switch-control;
                    description "Resource temporarily chosen by control configuration where the resource is not the preferred resource.
                        Preferred resource has highest priority.
                        Temporarily overrides reversion.
                        If this resource fails it will NOT switch. 
                        If resource selected is shared and another FC requires the resource through a FORCE on that FC and the FC is of a higher FcPriority then the selection control on this FC will change to NORMAL and switch to best available based upon normal rules.
                        If the resource selected is then set to LOCK_OUT then the selection control will change to NORMAL and switch to best available based upon normal rules.
                        Can be returned to NORMAL by configuration action.";
                }
                identity SWITCH_STATE_REASON {
                    description "none";
                }
                identity REVERSION_MODE {
                    description "none";
                }
                identity REVERSION_MODE_REVERTIVE {
                    base reversion-mode;
                    description "An FC switched to a lower priority (non-preferred) resource will revert to a higher priority (preferred) resource when that recovers (potentially after some hold-off time).";
                }
                identity REVERSION_MODE_NON-REVERTIVE {
                    base reversion-mode;
                    description "An FC switched to a lower priority (non-preferred) resource will not revert to a higher priority (preferred) resource when that recovers.";
                }
                identity RESILIENCE_CONTROL {
                    description "none";
                }
                identity RESILIENCE_CONTROL_QUIESCENT {
                    base resilience-control;
                    description "none";
                }
                identity RESILIENCE_CONTROL_RESTORING {
                    base resilience-control;
                    description "none";
                }
                identity RESILIENCE_CONTROL_RECOVERY_FAILED {
                    base resilience-control;
                    description "none";
                }
                identity RESILIENCE_CONTROL_UNKNOWN {
                    base resilience-control;
                    description "none";
                }
                identity RUN_MODE {
                    description "none";
                }
                identity RUN_MODE_FREE_RUN {
                    base run-mode;
                    description "The ckock is not synchronized to another clock.";
                }
                identity RUN_MODE_LOCKED {
                    base run-mode;
                    description "The clock is synchronised to another clock.";
                }
                identity RUN_MODE_HOLD_OVER {
                    base run-mode;
                    description "The clock was previously synchonised to another clock but that timing input has been lost.
                        The clock is set to the last known synchronization.";
                }
                identity OPERATIONAL_STATE {
                    description "none";
                }
                identity OPERATIONAL_STATE_DISABLED {
                    base operational-state;
                    description "The resource is unable to meet the SLA of the user of the resource. 
                        If no (explicit) SLA is defined the resource is disabled if it is totally inoperable and unable to provide service to the user.";
                }
                identity OPERATIONAL_STATE_ENABLED {
                    base operational-state;
                    description "The resource is partially or fully operable and available for use.";
                }
                identity ADMINISTRATIVE_STATE {
                    description "none";
                }
                identity ADMINISTRATIVE_STATE_LOCKED {
                    base administrative-state;
                    description "Users are administratively prohibited from making use of the resource.";
                }
                identity ADMINISTRATIVE_STATE_UNLOCKED {
                    base administrative-state;
                    description "Users are allowed to use the resource.";
                }
                identity ADMINISTRATIVE_STATE_SHUTTING_DOWN {
                    base administrative-state;
                    description "The entity is administratively restricted to existing instances of use only. There may be specific actions to remove existing uses. No new instances of use can be enabled.
                        The resource automatically transitions to “locked” when the last user quits. 
                        The administrative state is not visible in the client context. 
                        The lifecycle state “pending removal” should be used to indicate to the client that the provider intends to remove the resource.";
                }
                identity ADMINISTRATIVE_CONTROL {
                    description "none";
                }
                identity ADMINISTRATIVE_CONTROL_UNLOCK {
                    base administrative-control;
                    description "The intention is for the entity to become unlocked.
                        The entity may already be UNLOCKED.";
                }
                identity ADMINISTRATIVE_CONTROL_LOCK_PASSIVE {
                    base administrative-control;
                    description "The intention is for the entity to become locked but no effort is expected to move to the Locked state (the state will be achieved once all users stop using the resource). 
                        The entity may be LOCKED.";
                }
                identity ADMINISTRATIVE_CONTROL_LOCK_ACTIVE {
                    base administrative-control;
                    description "The intention is for the entity to become locked and it is expected that effort will be made to move to the Locked state (users will be actively removed). 
                        The entity may already be LOCKED.";
                }
                identity ADMINISTRATIVE_CONTROL_LOCK_IMMEDIATE {
                    base administrative-control;
                    description "The intention is for the entity to become locked and it is expected to move to the Locked state immediately (users will be force removed). 
                        The entity may already be LOCKED.";
                }
                identity ADMINISTRATIVE_CONTROL_QUIESCENT {
                    base administrative-control;
                    description "The administrative state is at a stable value (LOCKED/UNLOCKED) and no action is being taken.";
                }
                identity LIFECYCLE_STATE {
                    description "none";
                }
                identity LIFECYCLE_STATE_PLANNED {
                    base lifecycle-state;
                    description "The resource is planned but is not present in the network.
                        Should include a 'time' when the resources are expected to be installed.";
                }
                identity LIFECYCLE_STATE_POTENTIAL_AVAILABLE {
                    base lifecycle-state;
                    description "The supporting resources are present in the network but are shared with other clients; or require further configuration before they can be used; or both.
                        (1) When a potential resource is configured and allocated to a client it is moved to the INSTALLED state for that client.
                        (2) If the potential resource has been consumed (e.g. allocated to another client) it is moved to the POTENTIAL BUSY state for all other clients.";
                }
                identity LIFECYCLE_STATE_POTENTIAL_BUSY {
                    base lifecycle-state;
                    description "The supporting resources are present in the network but have been allocated to other clients.";
                }
                identity LIFECYCLE_STATE_INSTALLED {
                    base lifecycle-state;
                    description "The resource is present in the network and is capable of providing the service.";
                }
                identity LIFECYCLE_STATE_PENDING_REMOVAL {
                    base lifecycle-state;
                    description "The resource has been marked for removal.  Should include a “time” when the resources are expected to be removed.";
                }
                identity BLOCK_DIRECTION {
                    description "none";
                }
                identity BLOCK_DIRECTION_NO_BLOCK {
                    base block-direction;
                    description "none";
                }
                identity ACTION_VERBS {
                    description "none";
                }
                identity ACTION_VERBS_CREATE_POST_ADD {
                    base action-verbs;
                    description "none";
                }
                identity ACTION_VERBS_SET_UPDATE_PUT_MODIFY_WRITE_ADD {
                    base action-verbs;
                    description "none";
                }
                identity ACTION_VERBS_GET_READ {
                    base action-verbs;
                    description "none";
                }
                identity ACTION_VERBS_DELETE_REMOVE {
                    base action-verbs;
                    description "none";
                }
                identity ACTIVITY_DIRECTIVE {
                    description "none";
                }
                identity ACTIVITY_DIRECTIVE_STRUCTURE_IS_NOT {
                    base activity-directive;
                    description "none";
                }
                identity ACTIVITY_DIRECTIVE_NEW_STRUCTURE_AND_VALUES {
                    base activity-directive;
                    description "none";
                }
                identity ACTIVITY_DIRECTIVE_INCREMENTAL_STRUCTURE_AND_VALUES {
                    base activity-directive;
                    description "none";
                }
                identity ACTIVITY_DIRECTIVE_ONLY_VALUES_IN_EXISTING_STRUCTURE {
                    base activity-directive;
                    description "none";
                }
                identity ACTIVITY_DIRECTIVE_DEFINED_BY_VERB {
                    base activity-directive;
                    description "none";
                }
                identity ACTION_EFFORT {
                    description "none";
                }
                identity ACTION_EFFORT_BEST_EFFORT {
                    base action-effort;
                    description "none";
                }
                identity ACTION_EFFORT_EXACT_MATCH {
                    base action-effort;
                    description "none";
                }
                identity PAUSE_RESUME_RULE {
                    description "none";
                }
                identity PAUSE_RESUME_RULE_NO_PAUSE_POSSIBLE {
                    base pause-resume-rule;
                    description "none";
                }
                identity CONNECTOR_AND_PIN_ORIENTATION {
                    description "none";
                }
                identity CONNECTOR_AND_PIN_ORIENTATION_MALE {
                    base connector-and-pin-orientation;
                    description "The connecting elements are dominantly protrusions.";
                }
                identity CONNECTOR_AND_PIN_ORIENTATION_FEMALE {
                    base connector-and-pin-orientation;
                    description "The connecting elements are dominantly indentations.";
                }
                identity CONNECTOR_AND_PIN_ORIENTATION_SYMMETRIC_NEUTRAL {
                    base connector-and-pin-orientation;
                    description "The pin (and housing) orientation combination is such that it is symmetric so a connector is compatible with itself.
                        The connecting element may be a surface rather than protrusions or indentations.";
                }
                identity EQUIPMENT_CATEGORY {
                    description "none";
                }
                identity EQUIPMENT_CATEGORY_SUBRACK {
                    base equipment-category;
                    description "An assembly with holders designed to accommodate CIRCUIT_PACKs. 
                        The assembly is designed to be mounted in a RACK.";
                }
                identity EQUIPMENT_CATEGORY_CIRCUIT_PACK {
                    base equipment-category;
                    description "An assembly with connectors compatible with those in a holder.
                        The assembly is designed to be mounted in a holder (SLOT) of a SUBRACK.
                        May also support holders (SLOTs) for SMALL_FORMFACTOR_PLUGGABLEs.";
                }
                identity EQUIPMENT_CATEGORY_SMALL_FORMFACTOR_PLUGGABLE {
                    base equipment-category;
                    description "A small assembly (compared to a CIRCUIT_PACK) with connectors compatible with those in a holder.
                        The assembly is designed to be mounted in a holder (SLOT) of a CIRCUIT_PACK or STAND_ALONE_UNIT.";
                }
                identity EQUIPMENT_CATEGORY_STAND_ALONE_UNIT {
                    base equipment-category;
                    description "An assembly with connectors for cabling and potentially with holders.
                        The assembly is designed to be mounted in a freeform environment (on a table or simple mechanical cabinet).
                        May support holders (SLOTs) for CIRCUIT_PACKs or for SMALL_FORMFACTOR_PLUGGABLEs.";
                }
                identity EQUIPMENT_CATEGORY_RACK {
                    base equipment-category;
                    description "A mechanical assembly with cabling and predefined mounting points for particular SUBRACK types.
                        The assembly is designed to be mounted on the floor in a row with other RACKs.";
                }
                identity HOLDER_CATEGORY {
                    description "none";
                }
                identity HOLDER_CATEGORY_SLOT {
                    base holder-category;
                    description "A guided holder with fixed connectors.
                        The guided holder is designed to take a particular form of CIRCUIT_PACK or SMALL_FORMFACTOR_PLUGGABLE";
                }
                identity FORWARDING_RULE {
                    description "none";
                }
                identity FORWARDING_RULE_CANNOT_FORWARD_ACROSS_FD_LINK {
                    base forwarding-rule;
                    description "LTPs referenced by the FD (or indirectly by the Link between FDs) cannot have FCs created between them.
                        This rule overrides all others.";
                }
                identity FORWARDING_RULE_MUST_FORWARD_ACROSS_FD_LINK {
                    base forwarding-rule;
                    description "LTPs referenced by the FD (or indirectly by the Link between FDs) MUST have FCs created between them.
                        This rule overrides all others except the CANNOT_FORWARD rule.";
                }
                identity FORWARDING_RULE_MAY_FORWARD_ACROSS_FD_LINK {
                    base forwarding-rule;
                    description "LTPs referenced by the FD (or indirectly by the Link between FDs) may have FCs created between them.
                        FCs may not be created between points that are not related by this rule either directly in an FD or indirectly via a Link linking two or more FDs.
                        For a Link points in an FD at one end of the Link can be connected to points in an FD at an other end of the Link.";
                }
                identity FORWARDING_RULE_NULL_FORWARDING_RULE {
                    base forwarding-rule;
                    description "none";
                }
                identity RULE_TYPE {
                    description "none";
                }
                identity RULE_TYPE_FORWARDING {
                    base rule-type;
                    description "The rule relates to creation of FCs.";
                }
                identity RULE_TYPE_COST {
                    base rule-type;
                    description "The rule relates to forwarding cost.";
                }
                identity RULE_TYPE_RISK {
                    base rule-type;
                    description "The rule relates to forwarding risk.";
                }
                identity RULE_TYPE_CAPACITY {
                    base rule-type;
                    description "none";
                }
                identity PORT_ROLE_RULE {
                    description "none";
                }
                identity PORT_ROLE_RULE_SAME_ROLE {
                    base port-role-rule;
                    description "none";
                }
                identity PORT_ROLE_RULE_DIFFERENT_ROLE {
                    base port-role-rule;
                    description "none";
                }
                identity PORT_ROLE_RULE_ANY_ROLE {
                    base port-role-rule;
                    description "none";
                }
                identity SIGNAL_PROPERTY_VALUE_RULE {
                    description "none";
                }
                identity SIGNAL_PROPERTY_VALUE_RULE_SAME_VALUE {
                    base signal-property-value-rule;
                    description "none";
                }
                identity SIGNAL_PROPERTY_VALUE_RULE_ANY_VALUE {
                    base signal-property-value-rule;
                    description "none";
                }
                identity TERMINATION_DIRECTION {
                    description "none";
                }
                identity TERMINATION_DIRECTION_BIDIRECTIONAL {
                    base termination-direction;
                    description "A Termination with both SINK and SOURCE flows.";
                }
                identity TERMINATION_DIRECTION_SINK {
                    base termination-direction;
                    description "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity.";
                }
                identity TERMINATION_DIRECTION_SOURCE {
                    base termination-direction;
                    description "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity.";
                }
                identity TERMINATION_DIRECTION_UNDEFINED_OR_UNKNOWN {
                    base termination-direction;
                    description "Not a normal state. The system is unable to determine the correct value.";
                }
                identity TERMINATION_DIRECTION {
                    description "none";
                }
                identity TERMINATION_DIRECTION_BIDIRECTIONAL {
                    base termination-direction;
                    description "A Termination with both SINK and SOURCE flows.";
                }
                identity TERMINATION_DIRECTION_SINK {
                    base termination-direction;
                    description "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base termination-direction;
                    description "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base termination-direction;
                    description "Not a normal state. The system is unable to determine the correct value.";
                }
                identity ACTION_VERBS {
                    description "none";
                }
                identity ACTION_VERBS_CREATE_POST_ADD {
                    base action-verbs;
                    description "none";
                }
                identity ACTION_VERBS_SET_UPDATE_PUT_MODIFY_WRITE_ADD {
                    base action-verbs;
                    description "none";
                }
                identity ACTION_VERBS_GET_READ {
                    base action-verbs;
                    description "none";
                }
                identity ACTION_VERBS_DELETE_REMOVE {
                    base action-verbs;
                    description "none";
                }
                identity DIRECTION {
                    description "none";
                }
                identity DIRECTION_IN {
                    base direction;
                    description "none";
                }
                identity DIRECTION_OUT {
                    base direction;
                    description "none";
                }
                identity DIRECTION_BIDIRECTIONAL {
                    base direction;
                    description "none";
                }
                typedef operational-state {
                    type identityref {
                        base operational-state;
                    }
                    description "The operational state is used to indicate whether or not the resource is installed and working. ";
                }
                typedef administrative-state {
                    type identityref {
                        base administrative-state;
                    }
                    description "The administrative state is used to show whether use of a resource is allowed or prohibited.
                        The administrative state can be observed and directly controlled by a certain operational roles. 
                        Typically, only a user (in the provider context) with administrative privileges is allowed to write the administrative state, any other users are restricted to read only.";
                }
                typedef administrative-control {
                    type identityref {
                        base administrative-control;
                    }
                    description "Reflects the current control action when the entity is not in the desired state.";
                }
                typedef lifecycle-state {
                    type identityref {
                        base lifecycle-state;
                    }
                    description "This state is used to track the planned deployment, allocation to clients and withdrawal of resources.";
                }

            /***********************
            * package state-machines
            **********************/ 



    /***********************
    * package core-model-enhancements
    **********************/ 
        /***********************
        * package fc-switch-enhancements-developed
        **********************/ 
            /***********************
            * package type-definitions
            **********************/ 
                identity PORT_DIRECTION {
                    description "none";
                }
                identity PORT_DIRECTION_BIDIRECTIONAL {
                    base port-direction;
                    description "The Port has both an INPUT flow and an OUTPUT flow defined.";
                }
                identity PORT_DIRECTION_INPUT {
                    base port-direction;
                    description "The Port only has definition for a flow into the Forwarding entity (i.e. an ingress flow).";
                }
                identity PORT_DIRECTION_OUTPUT {
                    base port-direction;
                    description "The Port only has definition for a flow out of the Forwarding entity (i.e. an egress flow).";
                }
                identity PORT_DIRECTION_UNIDENTIFIED_OR_UNKNOWN {
                    base port-direction;
                    description "Not a normal state. The system is unable to determine the correct value.";
                }
                identity PORT_DIRECTION_OMNIDIRECTIONAL {
                    base port-direction;
                    description "none";
                }
                identity FORWARDING_DIRECTION {
                    description "none";
                }
                identity FORWARDING_DIRECTION_BIDIRECTIONAL {
                    base forwarding-direction;
                    description "The Forwarding entity supports both BIDIRECTIONAL flows at all Ports (i.e. all Ports have both an INPUT flow and an OUTPUT flow defined).";
                }
                identity FORWARDING_DIRECTION_UNIDIRECTIONAL {
                    base forwarding-direction;
                    description "The Forwarding entity has Ports that are either INPUT or OUTPUT. It has no BIDIRECTIONAL Ports.";
                }
                identity FORWARDING_DIRECTION_UNDEFINED_OR_UNKNOWN {
                    base forwarding-direction;
                    description "Not a normal state. The system is unable to determine the correct value.";
                }
                identity FORWARDING_DIRECTION_OMNIDIRECTIONAL {
                    base forwarding-direction;
                    description "none";
                }
                identity TERMINATION_DIRECTION {
                    description "none";
                }
                identity TERMINATION_DIRECTION_BIDIRECTIONAL {
                    base termination-direction;
                    description "A Termination with both SINK and SOURCE flows.";
                }
                identity TERMINATION_DIRECTION_SINK {
                    base termination-direction;
                    description "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base termination-direction;
                    description "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base termination-direction;
                    description "Not a normal state. The system is unable to determine the correct value.";
                }
                identity EXTENDED_TERMINATION_DIRECTION {
                    description "none";
                }
                identity EXTENDED_TERMINATION_DIRECTION_CONTRA_DIRECTION_SINK {
                    base extended-termination-direction;
                    description "The essential flow of the Termination entity is SINK (i.e. up the layer stack) but the INPUT flow of the Termination entity was provided by a SOURCE OUTPUT or taken from a SOURCE INPUT (duplicating the input signal) hence reversing the flow orientation from down the layer stack to up the layer stack.";
                }
                identity EXTENDED_TERMINATION_DIRECTION_CONTRA_DIRECTION_SOURCE {
                    base extended-termination-direction;
                    description "The essential flow of the Termination entity is SOURCE (i.e. down the layer stack) but the OUTPUT flow of the Termination entity was fed to (and replaces) a SINK OUTPUT or was fed to a SINK INPUT (replacing the normal flow) hence reversing the flow orientation from down the layer stack to up the layer stack.";
                }
                identity TERMINATION_STATE {
                    description "none";
                }
                identity TERMINATION_STATE_LP_CAN_NEVER_TERMINATE {
                    base termination-state;
                    description "A non-flexible case that can never be terminated.";
                }
                identity TERMINATION_STATE_LP_NOT_TERMINATED {
                    base termination-state;
                    description "A flexible termination that can terminate but is currently not terminated.";
                }
                identity TERMINATION_STATE_TERMINATED_SERVER_TO_CLIENT_FLOW {
                    base termination-state;
                    description "A flexible termination that is currently terminated for server to client flow only.";
                }
                identity TERMINATION_STATE_TERMINATED_CLIENT_TO_SERVER_FLOW {
                    base termination-state;
                    description "A flexible termination that is currently terminated for client to server flow only.";
                }
                identity TERMINATION_STATE_TERMINATED_BIDIRECTIONAL {
                    base termination-state;
                    description "A flexible termination that is currently terminated in both directions of flow.";
                }
                identity TERMINATION_STATE_LP_PERMENANTLY_TERMINATED {
                    base termination-state;
                    description "A non-flexible termination that is always terminated (in both directions of flow for a bidirectional case and in the one direction of flow for both unidirectional cases).";
                }
                identity TERMINATION_STATE_TERMINATION_STATE_UNKNOWN {
                    base termination-state;
                    description "There TerminationState cannot be determined.";
                }
                identity PROTECTION_REASON {
                    description "none";
                }
                identity PROTECTION_REASON_WAIT_TO_REVERT {
                    base protection-reason;
                    description "The resource is selected as control is waiting to restore to a preferred resource.";
                }
                identity PROTECTION_REASON_SIGNAL_DEGRADE {
                    base protection-reason;
                    description "The resource is selected as the best preferred resource is in signal degrade.";
                }
                identity PROTECTION_REASON_SIGNAL_FAIL {
                    base protection-reason;
                    description "The resource is selected as the best preferred resource is in signal fail.";
                }
                identity ROUTE_SELECTION_CONTROL {
                    description "none";
                }
                identity ROUTE_SELECTION_CONTROL_LOCK_OUT {
                    base route-selection-control;
                    description "The resource is configured to temporarily not be available for use in the protection scheme(s) it is part of.
                        This overrides all other protection control states including forced.
                        If the item is locked out, then it cannot be used under any circumstances.
                        Note: Only relevant when part of a protection scheme.
                        Note: if a protection process that has a relationship to the item (i.e. is one of the options the protection process may choose) is deactivated by being isFrozen = true) then the lockout request will be rejected. ";
                }
                identity ROUTE_SELECTION_REASON {
                    description "none";
                }
                identity SWITCH_CONTROL {
                    description "none";
                }
                identity SWITCH_CONTROL_NORMAL {
                    base switch-control;
                    description "No administrative control applied to the switch.";
                }
                identity SWITCH_CONTROL_MANUAL {
                    base switch-control;
                    description "Resource temporarily chosen by control configuration where the resource is not the preferred resource.
                        Preferred resource has highest priority.
                        Temporarily overrides reversion.
                        If this resource fails, it will switch to best available resource. 
                        If resource selected is shared and another FC requires the resource, then the selection control will change to Normal and switch to best available based upon normal rules.
                        Cannot manually switch a Forced switch, cannot remove a forced switch, cannot switch to a locked out item and will be rejected if the protection process is deactivated by being Freeze = true).
                        A manual switch/route that is selecting an FcPort, LTP, FC, Link or Route that is subsequently set to LOCK_OUT will have the manual removed (changed to NORMAL) and will switch away from the  FcPort with LOCK_OUT to best available based upon normal rules.
                        A manual switch that is selecting an FcPort that is subsequently selected by a Forced switch will be restored to normal operation and the manual will be removed.
                        A manual switch/route that is selecting an FcPort, LTP, FC, Link or Route that is subsequently manual selected by another switch/route  will have the manual removed and will switch away from the FcPort.
                        Can be returned to NORMAL by configuration action.";
                }
                identity SWITCH_CONTROL_FORCED {
                    base switch-control;
                    description "Resource temporarily chosen by control configuration where the resource is not the preferred resource.
                        Preferred resource has highest priority.
                        Temporarily overrides reversion.
                        If this resource fails it will NOT switch. 
                        If resource selected is shared and another FC requires the resource through a FORCE on that FC and the FC is of a higher FcPriority then the selection control on this FC will change to NORMAL and switch to best available based upon normal rules.
                        If the resource selected is then set to LOCK_OUT then the selection control will change to NORMAL and switch to best available based upon normal rules.
                        Can be returned to NORMAL by configuration action.";
                }
                identity SWITCH_STATE_REASON {
                    description "none";
                }
                identity REVERSION_MODE {
                    description "none";
                }
                identity REVERSION_MODE_REVERTIVE {
                    base reversion-mode;
                    description "An FC switched to a lower priority (non-preferred) resource will revert to a higher priority (preferred) resource when that recovers (potentially after some hold-off time).";
                }
                identity REVERSION_MODE_NON-REVERTIVE {
                    base reversion-mode;
                    description "An FC switched to a lower priority (non-preferred) resource will not revert to a higher priority (preferred) resource when that recovers.";
                }
                identity RESILIENCE_CONTROL {
                    description "none";
                }
                identity RESILIENCE_CONTROL_QUIESCENT {
                    base resilience-control;
                    description "none";
                }
                identity RESILIENCE_CONTROL_RESTORING {
                    base resilience-control;
                    description "none";
                }
                identity RESILIENCE_CONTROL_RECOVERY_FAILED {
                    base resilience-control;
                    description "none";
                }
                identity RESILIENCE_CONTROL_UNKNOWN {
                    base resilience-control;
                    description "none";
                }
                identity RUN_MODE {
                    description "none";
                }
                identity RUN_MODE_FREE_RUN {
                    base run-mode;
                    description "The ckock is not synchronized to another clock.";
                }
                identity RUN_MODE_LOCKED {
                    base run-mode;
                    description "The clock is synchronised to another clock.";
                }
                identity RUN_MODE_HOLD_OVER {
                    base run-mode;
                    description "The clock was previously synchonised to another clock but that timing input has been lost.
                        The clock is set to the last known synchronization.";
                }
                identity OPERATIONAL_STATE {
                    description "none";
                }
                identity OPERATIONAL_STATE_DISABLED {
                    base operational-state;
                    description "The resource is unable to meet the SLA of the user of the resource. 
                        If no (explicit) SLA is defined the resource is disabled if it is totally inoperable and unable to provide service to the user.";
                }
                identity OPERATIONAL_STATE_ENABLED {
                    base operational-state;
                    description "The resource is partially or fully operable and available for use.";
                }
                identity ADMINISTRATIVE_STATE {
                    description "none";
                }
                identity ADMINISTRATIVE_STATE_LOCKED {
                    base administrative-state;
                    description "Users are administratively prohibited from making use of the resource.";
                }
                identity ADMINISTRATIVE_STATE_UNLOCKED {
                    base administrative-state;
                    description "Users are allowed to use the resource.";
                }
                identity ADMINISTRATIVE_STATE_SHUTTING_DOWN {
                    base administrative-state;
                    description "The entity is administratively restricted to existing instances of use only. There may be specific actions to remove existing uses. No new instances of use can be enabled.
                        The resource automatically transitions to “locked” when the last user quits. 
                        The administrative state is not visible in the client context. 
                        The lifecycle state “pending removal” should be used to indicate to the client that the provider intends to remove the resource.";
                }
                identity ADMINISTRATIVE_CONTROL {
                    description "none";
                }
                identity ADMINISTRATIVE_CONTROL_UNLOCK {
                    base administrative-control;
                    description "The intention is for the entity to become unlocked.
                        The entity may already be UNLOCKED.";
                }
                identity ADMINISTRATIVE_CONTROL_LOCK_PASSIVE {
                    base administrative-control;
                    description "The intention is for the entity to become locked but no effort is expected to move to the Locked state (the state will be achieved once all users stop using the resource). 
                        The entity may be LOCKED.";
                }
                identity ADMINISTRATIVE_CONTROL_LOCK_ACTIVE {
                    base administrative-control;
                    description "The intention is for the entity to become locked and it is expected that effort will be made to move to the Locked state (users will be actively removed). 
                        The entity may already be LOCKED.";
                }
                identity ADMINISTRATIVE_CONTROL_LOCK_IMMEDIATE {
                    base administrative-control;
                    description "The intention is for the entity to become locked and it is expected to move to the Locked state immediately (users will be force removed). 
                        The entity may already be LOCKED.";
                }
                identity ADMINISTRATIVE_CONTROL_QUIESCENT {
                    base administrative-control;
                    description "The administrative state is at a stable value (LOCKED/UNLOCKED) and no action is being taken.";
                }
                identity LIFECYCLE_STATE {
                    description "none";
                }
                identity LIFECYCLE_STATE_PLANNED {
                    base lifecycle-state;
                    description "The resource is planned but is not present in the network.
                        Should include a 'time' when the resources are expected to be installed.";
                }
                identity LIFECYCLE_STATE_POTENTIAL_AVAILABLE {
                    base lifecycle-state;
                    description "The supporting resources are present in the network but are shared with other clients; or require further configuration before they can be used; or both.
                        (1) When a potential resource is configured and allocated to a client it is moved to the INSTALLED state for that client.
                        (2) If the potential resource has been consumed (e.g. allocated to another client) it is moved to the POTENTIAL BUSY state for all other clients.";
                }
                identity LIFECYCLE_STATE_POTENTIAL_BUSY {
                    base lifecycle-state;
                    description "The supporting resources are present in the network but have been allocated to other clients.";
                }
                identity LIFECYCLE_STATE_INSTALLED {
                    base lifecycle-state;
                    description "The resource is present in the network and is capable of providing the service.";
                }
                identity LIFECYCLE_STATE_PENDING_REMOVAL {
                    base lifecycle-state;
                    description "The resource has been marked for removal.  Should include a “time” when the resources are expected to be removed.";
                }
                identity BLOCK_DIRECTION {
                    description "none";
                }
                identity BLOCK_DIRECTION_NO_BLOCK {
                    base block-direction;
                    description "none";
                }
                identity ACTION_VERBS {
                    description "none";
                }
                identity ACTION_VERBS_CREATE_POST_ADD {
                    base action-verbs;
                    description "none";
                }
                identity ACTION_VERBS_SET_UPDATE_PUT_MODIFY_WRITE_ADD {
                    base action-verbs;
                    description "none";
                }
                identity ACTION_VERBS_GET_READ {
                    base action-verbs;
                    description "none";
                }
                identity ACTION_VERBS_DELETE_REMOVE {
                    base action-verbs;
                    description "none";
                }
                identity ACTIVITY_DIRECTIVE {
                    description "none";
                }
                identity ACTIVITY_DIRECTIVE_STRUCTURE_IS_NOT {
                    base activity-directive;
                    description "none";
                }
                identity ACTIVITY_DIRECTIVE_NEW_STRUCTURE_AND_VALUES {
                    base activity-directive;
                    description "none";
                }
                identity ACTIVITY_DIRECTIVE_INCREMENTAL_STRUCTURE_AND_VALUES {
                    base activity-directive;
                    description "none";
                }
                identity ACTIVITY_DIRECTIVE_ONLY_VALUES_IN_EXISTING_STRUCTURE {
                    base activity-directive;
                    description "none";
                }
                identity ACTIVITY_DIRECTIVE_DEFINED_BY_VERB {
                    base activity-directive;
                    description "none";
                }
                identity ACTION_EFFORT {
                    description "none";
                }
                identity ACTION_EFFORT_BEST_EFFORT {
                    base action-effort;
                    description "none";
                }
                identity ACTION_EFFORT_EXACT_MATCH {
                    base action-effort;
                    description "none";
                }
                identity PAUSE_RESUME_RULE {
                    description "none";
                }
                identity PAUSE_RESUME_RULE_NO_PAUSE_POSSIBLE {
                    base pause-resume-rule;
                    description "none";
                }
                identity CONNECTOR_AND_PIN_ORIENTATION {
                    description "none";
                }
                identity CONNECTOR_AND_PIN_ORIENTATION_MALE {
                    base connector-and-pin-orientation;
                    description "The connecting elements are dominantly protrusions.";
                }
                identity CONNECTOR_AND_PIN_ORIENTATION_FEMALE {
                    base connector-and-pin-orientation;
                    description "The connecting elements are dominantly indentations.";
                }
                identity CONNECTOR_AND_PIN_ORIENTATION_SYMMETRIC_NEUTRAL {
                    base connector-and-pin-orientation;
                    description "The pin (and housing) orientation combination is such that it is symmetric so a connector is compatible with itself.
                        The connecting element may be a surface rather than protrusions or indentations.";
                }
                identity EQUIPMENT_CATEGORY {
                    description "none";
                }
                identity EQUIPMENT_CATEGORY_SUBRACK {
                    base equipment-category;
                    description "An assembly with holders designed to accommodate CIRCUIT_PACKs. 
                        The assembly is designed to be mounted in a RACK.";
                }
                identity EQUIPMENT_CATEGORY_CIRCUIT_PACK {
                    base equipment-category;
                    description "An assembly with connectors compatible with those in a holder.
                        The assembly is designed to be mounted in a holder (SLOT) of a SUBRACK.
                        May also support holders (SLOTs) for SMALL_FORMFACTOR_PLUGGABLEs.";
                }
                identity EQUIPMENT_CATEGORY_SMALL_FORMFACTOR_PLUGGABLE {
                    base equipment-category;
                    description "A small assembly (compared to a CIRCUIT_PACK) with connectors compatible with those in a holder.
                        The assembly is designed to be mounted in a holder (SLOT) of a CIRCUIT_PACK or STAND_ALONE_UNIT.";
                }
                identity EQUIPMENT_CATEGORY_STAND_ALONE_UNIT {
                    base equipment-category;
                    description "An assembly with connectors for cabling and potentially with holders.
                        The assembly is designed to be mounted in a freeform environment (on a table or simple mechanical cabinet).
                        May support holders (SLOTs) for CIRCUIT_PACKs or for SMALL_FORMFACTOR_PLUGGABLEs.";
                }
                identity EQUIPMENT_CATEGORY_RACK {
                    base equipment-category;
                    description "A mechanical assembly with cabling and predefined mounting points for particular SUBRACK types.
                        The assembly is designed to be mounted on the floor in a row with other RACKs.";
                }
                identity HOLDER_CATEGORY {
                    description "none";
                }
                identity HOLDER_CATEGORY_SLOT {
                    base holder-category;
                    description "A guided holder with fixed connectors.
                        The guided holder is designed to take a particular form of CIRCUIT_PACK or SMALL_FORMFACTOR_PLUGGABLE";
                }
                identity FORWARDING_RULE {
                    description "none";
                }
                identity FORWARDING_RULE_CANNOT_FORWARD_ACROSS_FD_LINK {
                    base forwarding-rule;
                    description "LTPs referenced by the FD (or indirectly by the Link between FDs) cannot have FCs created between them.
                        This rule overrides all others.";
                }
                identity FORWARDING_RULE_MUST_FORWARD_ACROSS_FD_LINK {
                    base forwarding-rule;
                    description "LTPs referenced by the FD (or indirectly by the Link between FDs) MUST have FCs created between them.
                        This rule overrides all others except the CANNOT_FORWARD rule.";
                }
                identity FORWARDING_RULE_MAY_FORWARD_ACROSS_FD_LINK {
                    base forwarding-rule;
                    description "LTPs referenced by the FD (or indirectly by the Link between FDs) may have FCs created between them.
                        FCs may not be created between points that are not related by this rule either directly in an FD or indirectly via a Link linking two or more FDs.
                        For a Link points in an FD at one end of the Link can be connected to points in an FD at an other end of the Link.";
                }
                identity FORWARDING_RULE_NULL_FORWARDING_RULE {
                    base forwarding-rule;
                    description "none";
                }
                identity RULE_TYPE {
                    description "none";
                }
                identity RULE_TYPE_FORWARDING {
                    base rule-type;
                    description "The rule relates to creation of FCs.";
                }
                identity RULE_TYPE_COST {
                    base rule-type;
                    description "The rule relates to forwarding cost.";
                }
                identity RULE_TYPE_RISK {
                    base rule-type;
                    description "The rule relates to forwarding risk.";
                }
                identity RULE_TYPE_CAPACITY {
                    base rule-type;
                    description "none";
                }
                identity PORT_ROLE_RULE {
                    description "none";
                }
                identity PORT_ROLE_RULE_SAME_ROLE {
                    base port-role-rule;
                    description "none";
                }
                identity PORT_ROLE_RULE_DIFFERENT_ROLE {
                    base port-role-rule;
                    description "none";
                }
                identity PORT_ROLE_RULE_ANY_ROLE {
                    base port-role-rule;
                    description "none";
                }
                identity SIGNAL_PROPERTY_VALUE_RULE {
                    description "none";
                }
                identity SIGNAL_PROPERTY_VALUE_RULE_SAME_VALUE {
                    base signal-property-value-rule;
                    description "none";
                }
                identity SIGNAL_PROPERTY_VALUE_RULE_ANY_VALUE {
                    base signal-property-value-rule;
                    description "none";
                }
                identity TERMINATION_DIRECTION {
                    description "none";
                }
                identity TERMINATION_DIRECTION_BIDIRECTIONAL {
                    base termination-direction;
                    description "A Termination with both SINK and SOURCE flows.";
                }
                identity TERMINATION_DIRECTION_SINK {
                    base termination-direction;
                    description "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity.";
                }
                identity TERMINATION_DIRECTION_SOURCE {
                    base termination-direction;
                    description "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity.";
                }
                identity TERMINATION_DIRECTION_UNDEFINED_OR_UNKNOWN {
                    base termination-direction;
                    description "Not a normal state. The system is unable to determine the correct value.";
                }
                identity TERMINATION_DIRECTION {
                    description "none";
                }
                identity TERMINATION_DIRECTION_BIDIRECTIONAL {
                    base termination-direction;
                    description "A Termination with both SINK and SOURCE flows.";
                }
                identity TERMINATION_DIRECTION_SINK {
                    base termination-direction;
                    description "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base termination-direction;
                    description "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base termination-direction;
                    description "Not a normal state. The system is unable to determine the correct value.";
                }
                identity ACTION_VERBS {
                    description "none";
                }
                identity ACTION_VERBS_CREATE_POST_ADD {
                    base action-verbs;
                    description "none";
                }
                identity ACTION_VERBS_SET_UPDATE_PUT_MODIFY_WRITE_ADD {
                    base action-verbs;
                    description "none";
                }
                identity ACTION_VERBS_GET_READ {
                    base action-verbs;
                    description "none";
                }
                identity ACTION_VERBS_DELETE_REMOVE {
                    base action-verbs;
                    description "none";
                }
                identity DIRECTION {
                    description "none";
                }
                identity DIRECTION_IN {
                    base direction;
                    description "none";
                }
                identity DIRECTION_OUT {
                    base direction;
                    description "none";
                }
                identity DIRECTION_BIDIRECTIONAL {
                    base direction;
                    description "none";
                }
                typedef block-direction {
                    type identityref {
                        base termination-direction;
                        base block-direction;
                    }
                    description "none";
                }

            /***********************
            * package object-classes
            **********************/ 
                grouping network-scheme-specification {
                    leaf scheme-name {
                        type string;
                        description "none";
                    }
                    leaf external-definition-of-scheme {
                        type string;
                        description "none";
                    }
                    description "none";
                }
                grouping profile-proxy {
                    leaf profile-proxy-mode {
                        type string;
                        description "A parameter profile may be used in a number of different ways:
                            - Forces the values on the target with no opportunity to see or override the values in the target
                            - Sets the values on the target that can be seen on the target
                            - Sets the values on the target and supports override on the target so the target can be set away from the value in the profile
                            - etc.";
                    }
                    leaf control-parameters {
                        type leafref {
                            path '/core-model:network-control-domain/core-model:network-element/core-model:ltp/core-model:embedded-clock/core-model:encapsulated-fc/core-model:configuration-and-switch-control/core-model:control-parameters/core-model:';
                        }
                        description "The control parameters that can be set int the profile and applied to the target.
                            Not all parameters need be selected and applied.";
                    }
                    description "A lightweight sketch placeholder for the profile model.";
                }


        /***********************
        * package modeling-enhancements
        **********************/ 
            /***********************
            * package rules
            **********************/ 

            /***********************
            * package view-abstraction-rule-sketch
            **********************/ 
                grouping view-abstraction-rules {
                    leaf-list -ltp-relatest-to-ltp-in-other-view {
                        type string;
                        description "none";
                    }
                    description "Provides rules and access to policies that govern and explain the view abstraction.
                        At this point it appears that this is not necessary however it has been left in the model as there is still some view abstraction work to be done.";
                }

            /***********************
            * package lifecycle-dependency
            **********************/ 
                grouping lifecycle-scoping-class {
                    leaf-list composed-dependent {
                        type leafref {
                            path '/core-model:lifecycle-scoping-class/core-model:composed-dependent/core-model:';
                        }
                        description "none";
                    }
                    description "none";
                }
                grouping dependent-class {
                    leaf lifecycle-scoping-class {
                        type leafref {
                            path '/core-model:lifecycle-scoping-class/core-model:';
                        }
                        description "none";
                    }
                    leaf related-lifecycle-scoping-class {
                        type leafref {
                            path '/core-model:lifecycle-scoping-class/core-model:';
                        }
                        description "none";
                    }
                    description "none";
                }


        /***********************
        * package inter-view-relationships-sketch
        **********************/ 
            grouping sketch-fc {
                leaf supporting-fc-in-other-view {
                    type leafref {
                        path '/core-model:sketch-fc/core-model:';
                    }
                    description "none";
                }
                leaf-list suported-fc-in-other-view {
                    type leafref {
                        path '/core-model:sketch-fc/core-model:';
                    }
                    description "none";
                }
                description "none";
            }
            grouping sketch-ltp {
                leaf supporting-ltp-in-other-view {
                    type leafref {
                        path '/core-model:sketch-ltp/core-model:';
                    }
                    description "none";
                }
                leaf-list supported-ltp-in-other-view {
                    type leafref {
                        path '/core-model:sketch-ltp/core-model:';
                    }
                    description "none";
                }
                description "none";
            }

        /***********************
        * package enhancements-for-media
        **********************/ 
            /***********************
            * package object-classes
            **********************/ 
                grouping gain-characteristics {
                    description "none";
                }
                grouping filter-characteristics {
                    description "none";
                }


        /***********************
        * package essential-structure-sketch
        **********************/ 
            /***********************
            * package object-classes
            **********************/ 
                grouping attribute-package {
                    description "none";
                }
                grouping component {
                    leaf-list port {
                        type leafref {
                            path '/core-model:component/core-model:port/core-model:';
                        }
                        min-elements 1;
                        description "none";
                    }
                    leaf-list attribute-package {
                        type leafref {
                            path '/core-model:component/core-model:attribute-package/core-model:';
                        }
                        description "none";
                    }
                    leaf-list bound-component {
                        type leafref {
                            path '/core-model:component/core-model:';
                        }
                        description "none";
                    }
                    leaf encapsulated-system {
                        type leafref {
                            path '/core-model:system/core-model:';
                        }
                        description "none";
                    }
                    description "none";
                }
                grouping indivisible-flow-port {
                    leaf indivisiblefow-port {
                        type leafref {
                            path '/core-model:indivisible-flow-port/core-model:';
                        }
                        description "none";
                    }
                    leaf role {
                        type string;
                        description "none";
                    }
                    leaf-list indivisible-port-role-properties {
                        type leafref {
                            path '/core-model:indivisible-flow-port/core-model:indivisible-port-role-properties/core-model:';
                        }
                        min-elements 1;
                        description "none";
                    }
                    description "none";
                }
                grouping multi-flow-port {
                    leaf-list indivisible-flow-port {
                        type leafref {
                            path '/core-model:indivisible-flow-port/core-model:';
                        }
                        min-elements 1;
                        description "none";
                    }
                    leaf-list multi-flow-port {
                        type leafref {
                            path '/core-model:multi-flow-port/core-model:';
                        }
                        description "none";
                    }
                    description "none";
                }
                grouping port {
                    leaf role {
                        type string;
                        default "true";
                        description "none";
                    }
                    leaf bound-port {
                        type leafref {
                            path '/core-model:component/core-model:port/core-model:';
                        }
                        description "none";
                    }
                    leaf bound-component {
                        type leafref {
                            path '/core-model:component/core-model:';
                        }
                        description "none";
                    }
                    leaf port-role-properties {
                        type leafref {
                            path '/core-model:component/core-model:port/core-model:port-role-properties/core-model:';
                        }
                        description "none";
                    }
                    description "none";
                }
                grouping port-role-properties {
                    description "none";
                }
                grouping system {
                    description "none";
                }
                grouping indivisible-port-role-properties {
                    description "none";
                }



    /***********************
    * package core-operations-model
    **********************/ 
        /***********************
        * package data-types
        **********************/ 
            typedef ActionVerbs {
                type identityref {
                    base action-verbs;
                }
                description "none";
            }
            typedef TestType {
                type string;
                description "none";
            }
            typedef ActivityDirective {
                type identityref {
                    base activity-directive;
                }
                description "none";
            }
            typedef ActionEffort {
                type identityref {
                    base action-effort;
                }
                description "none";
            }
            typedef PauseResumeRule {
                type identityref {
                    base pause-resume-rule;
                }
                description "none";
            }

        /***********************
        * package object-classes
        **********************/ 
            grouping desired-outcome-constraints {
                leaf-list outcome-element {
                    type leafref {
                        path '/core-model:operation-envelope/core-model:operation-set/core-model:operation-details/core-model:desired-outcome-constraints/core-model:outcome-element/core-model:';
                    }
                    min-elements 1;
                    description "none";
                }
                leaf activity-directive {
                    type activity-directive;
                    description "none";
                }
                leaf has-delete-confirmation {
                    type boolean;
                    default "true";
                    description "none";
                }
                leaf number-of-instances-of-each-outcome-element {
                    type uint64;
                    default "1";
                    description "none";
                }
                description "none";
            }
            grouping element-constraints {
                leaf specific-class-structure {
                    type leafref {
                        path '/core-model:specific-class-structure/core-model:';
                    }
                    description "none";
                }
                leaf specific-pattern {
                    type leafref {
                        path '/core-model:specific-pattern/core-model:';
                    }
                    description "none";
                }
                description "none";
            }
            grouping general-directives {
                description "none";
            }
            grouping necessary-initial-condition-constraints {
                leaf is-not {
                    type boolean;
                    description "none";
                }
                description "none";
            }
            grouping operation-details {
                leaf action-verb {
                    type action-verbs;
                    description "none";
                }
                leaf-list necessary-initial-condition-constraints {
                    type leafref {
                        path '/core-model:operation-envelope/core-model:operation-set/core-model:operation-details/core-model:necessary-initial-condition-constraints/core-model:';
                    }
                    description "none";
                }
                leaf-list desired-outcome-constraints {
                    type leafref {
                        path '/core-model:operation-envelope/core-model:operation-set/core-model:operation-details/core-model:desired-outcome-constraints/core-model:';
                    }
                    min-elements 1;
                    description "none";
                }
                description "none";
            }
            grouping operation-envelope {
                leaf-list operation-set {
                    type leafref {
                        path '/core-model:operation-envelope/core-model:operation-set/core-model:';
                    }
                    min-elements 1;
                    description "none";
                }
                leaf general-directives {
                    type leafref {
                        path '/core-model:operation-envelope/core-model:general-directives/core-model:';
                    }
                    description "none";
                }
                leaf operation-identifiers {
                    type leafref {
                        path '/core-model:operation-envelope/core-model:operation-identifiers/core-model:';
                    }
                    description "none";
                }
                description "none";
            }
            grouping operation-identifiers {
                description "none";
            }
            grouping operation-set {
                leaf-list operation-set-that-must-have-started {
                    type leafref {
                        path '/core-model:operation-envelope/core-model:operation-set/core-model:';
                    }
                    description "none";
                }
                leaf-list operation-set-that-must-end {
                    type leafref {
                        path '/core-model:operation-envelope/core-model:operation-set/core-model:';
                    }
                    description "none";
                }
                leaf abort-after-duration-with-action-rule {
                    type to-be-defined;
                    description "none";
                }
                leaf effort-and-action {
                    type action-effort;
                    description "none";
                }
                leaf pause-resume-rule {
                    type pause-resume-rule;
                    description "none";
                }
                leaf-list operation-set {
                    type leafref {
                        path '/core-model:operation-envelope/core-model:operation-set/core-model:';
                    }
                    description "none";
                }
                leaf is-short-lived {
                    type boolean;
                    default "true";
                    description "none";
                }
                leaf-list operation-details {
                    type leafref {
                        path '/core-model:operation-envelope/core-model:operation-set/core-model:operation-details/core-model:';
                    }
                    min-elements 1;
                    description "none";
                }
                description "none";
            }
            grouping outcome-element-constraints {
                uses element-constraints;
                description "none";
            }
            grouping specific-class-structure {
                leaf class-type-name {
                    type leafref {
                        path '/core-model:ltp/core-model:';
                    }
                    description "none";
                }
                description "none";
            }
            grouping specific-pattern {
                description "none";
            }
            grouping ltp {
                description "none";
            }


    /***********************
    * package core-physical-model-initial
    **********************/ 
        /***********************
        * package rule-models
        **********************/ 
            /***********************
            * package fru-non-fru-rules
            **********************/ 
                /***********************
                * package object-classes
                **********************/ 
                    grouping field-replaceable {
                        leaf-list equipment-non-fru {
                            type leafref {
                                path '/core-model:field-replaceable/core-model:equipment-non-fru/core-model:';
                            }
                            description "none";
                        }
                        leaf-list holder {
                            type leafref {
                                path '/core-model:field-replaceable/core-model:holder/core-model:';
                            }
                            description "none";
                        }
                        leaf holder-address {
                            type leafref {
                                path '/core-model:field-replaceable/core-model:holder/core-model:';
                            }
                            description "none";
                        }
                        leaf-list connector {
                            type leafref {
                                path '/core-model:field-replaceable/core-model:connector/core-model:';
                            }
                            description "none";
                        }
                        uses equipment;
                        description "A rule class (an abstract specialization of Equipment) that represents an equipment that can be replaced in the field. 
                            May plug in to a holder in another equipment (if not stand-alone). 
                            Realization could use an FRU Boolean on Equipment.";
                    }
                    grouping non-field-replaceable {
                        uses equipment;
                        description "A rule class (an abstract specialization of Equipment) that represents an equipment that cannot be replaced in the field.
                            Is simply a subordinate part of an FRU (or another NFRU – where there must be an FRU at the top of the hierarchy). 
                            Does not have any exposed holders (any associated holders are assumed to belong to the containing FRU).
                            Does not have any connectors (any associated connectors are assumed to belong to the containing FRU).
                            ";
                    }


            /***********************
            * package connector-rules
            **********************/ 
                /***********************
                * package object-classes
                **********************/ 
                    grouping conector-in-holder {
                        leaf connector-on-equipment-for-holder {
                            type leafref {
                                path '/core-model:connector-on-equipment-for-holder/core-model:';
                            }
                            description "none";
                        }
                        uses connector;
                        description "A rule class (an abstract specialization of Connector) that represents a connector that are only accessible to an equipment inserted in the holder.";
                    }
                    grouping connector-cable-end {
                        leaf connector-on-equipment-for-cable {
                            type leafref {
                                path '/core-model:connector-on-equipment-for-cable/core-model:';
                            }
                            description "none";
                        }
                        uses connector;
                        description "A rule class (an abstract specialization of Connector) that represents a connector on the end of a cable.";
                    }
                    grouping connector-on-equipment-for-cable {
                        leaf connector-cable-end {
                            type leafref {
                                path '/core-model:connector-cable-end/core-model:';
                            }
                            description "none";
                        }
                        uses connector;
                        description "A rule class (an abstract specialization of Connector) that represents a connector exposed on an equipment such that a cable may be plugged in.";
                    }
                    grouping connector-on-equipment-for-holder {
                        leaf conector-in-holder {
                            type leafref {
                                path '/core-model:conector-in-holder/core-model:';
                            }
                            description "none";
                        }
                        uses connector;
                        description "A rule class (an abstract specialization of Connector) that represents a connector on an equipment that is intended to mate with a connector in a holder.";
                    }



        /***********************
        * package equipment-detail
        **********************/ 
            /***********************
            * package object-classes
            **********************/ 
                /***********************
                * package dynamic-details
                **********************/ 
                    grouping function-enablers {
                        leaf power-state {
                            type to-be-defined;
                            description "none";
                        }
                        description "Represents the dynamic aspects of the properties that relate to the motive force that directly enable functionality to emerge from the equipment.";
                    }
                    grouping mechanical-functions {
                        leaf rotation-speed {
                            type to-be-defined;
                            description "none";
                        }
                        description "Represents the dynamic aspects of the mechanical functions of the equipment.";
                    }
                    grouping physical-properties {
                        leaf temperature {
                            type to-be-defined;
                            description "none";
                        }
                        description "Represents the dynamic aspects of the physical environmental properties of the equipment.";
                    }
                    grouping holder-monitor {
                        leaf is-active {
                            type boolean;
                            description "none";
                        }
                        leaf is-actual-mismatch-with-expected {
                            type boolean;
                            description "none";
                        }
                        leaf aggregate-function {
                            type leafref {
                                path '/core-model:aggregate-function/core-model:';
                            }
                            description "none";
                        }
                        description "Represents the dynamic state of the holder instance. ";
                    }
                    grouping location {
                        container equipment-location {
                            uses address;
                            description "none";
                        }
                        container geographical-location {
                            uses address;
                            description "none";
                        }
                        description "Represents where the equipment is.";
                    }

                /***********************
                * package invariant-details
                **********************/ 
                    grouping equipment-structure {
                        leaf category {
                            type equipment-category;
                            description "This attribute provides the identifier for a category of equipments regarded as having particular shared characteristics.";
                        }
                        description "Represents the form of the equipment.";
                    }
                    grouping equipment-instance {
                        leaf manufacture-date {
                            type string;
                            description "This attribute represents the date on which this instance is manufactured.";
                        }
                        leaf serial-number {
                            type string;
                            description "This attribute represents the serial number of this instance.";
                        }
                        leaf asset-instance-identifier {
                            type string;
                            description "This attribute represents the asset identifier of this instance from the manufacturer's perspective.";
                        }
                        description "Represents the per instance invariant properties of the equipment.";
                    }
                    grouping equipment-type {
                        leaf description {
                            type string;
                            description "none";
                        }
                        leaf model-identifier {
                            type string;
                            description "none";
                        }
                        leaf part-type-identifier {
                            type string;
                            description "none";
                        }
                        leaf type-name {
                            type string;
                            description "none";
                        }
                        leaf version {
                            type string;
                            description "none";
                        }
                        description "Represents the invariant properties of the equipment that define and characterize the type.";
                    }
                    grouping holder-structure {
                        leaf holder-category {
                            type holder-category;
                            description "none";
                        }
                        leaf is-captive {
                            type boolean;
                            description "none";
                        }
                        leaf is-guided {
                            type boolean;
                            description "none";
                        }
                        leaf is-quantised-space {
                            type boolean;
                            description "none";
                        }
                        description "Represents the form of the holder.";
                    }
                    grouping manufactured-thing {
                        leaf manufacturer-properties {
                            type leafref {
                                path '/core-model:equipment/core-model:encapsulated-non-fru/core-model:exposed-cable/core-model:manufactured-thing/core-model:manufacturer-properties/core-model:';
                            }
                            description "none";
                        }
                        leaf equipment-type {
                            type leafref {
                                path '/core-model:equipment/core-model:encapsulated-non-fru/core-model:exposed-cable/core-model:manufactured-thing/core-model:equipment-type/core-model:';
                            }
                            description "none";
                        }
                        leaf equipment-instance {
                            type leafref {
                                path '/core-model:equipment/core-model:encapsulated-non-fru/core-model:exposed-cable/core-model:manufactured-thing/core-model:equipment-instance/core-model:';
                            }
                            description "none";
                        }
                        leaf operator-augmented-equipment-type {
                            type leafref {
                                path '/core-model:equipment/core-model:encapsulated-non-fru/core-model:exposed-cable/core-model:manufactured-thing/core-model:operator-augmented-equipment-type/core-model:';
                            }
                            description "none";
                        }
                        leaf operator-augmented-equipment-instance {
                            type leafref {
                                path '/core-model:equipment/core-model:encapsulated-non-fru/core-model:exposed-cable/core-model:manufactured-thing/core-model:operator-augmented-equipment-instance/core-model:';
                            }
                            description "none";
                        }
                        description "Collects all invariant aspects of a manufactured thing.";
                    }
                    grouping manufacturer-properties {
                        leaf manufacturer-identifier {
                            type string;
                            description "none";
                        }
                        leaf manufacturer-name {
                            type string;
                            description "none";
                        }
                        description "Represents the properties of the manufacturer.";
                    }
                    grouping mechanical-features {
                        description "Represents the invariant characteristics of dynamic mechanical features of a physical thing.";
                    }
                    grouping operator-augmented-equipment-type {
                        leaf asset-type-identifier {
                            type string;
                            description "none";
                        }
                        description "Represents the invariant properties of the equipment asset allocated by the operator that define and characterize the type.";
                    }
                    grouping physical-characteristics {
                        leaf weight-characeristics {
                            type to-be-defined;
                            description "none";
                        }
                        leaf fire-characteristics {
                            type to-be-defined;
                            description "none";
                        }
                        leaf materials {
                            type to-be-defined;
                            description "none";
                        }
                        description "Represents the invariant physical characteristics (including composition and physical robustness) of the type.";
                    }
                    grouping environmental-rating {
                        leaf thermal-rating {
                            type to-be-defined;
                            description "This attribute represents the thermal characteristics (preferred maximum/minimum, absolute maximum/minimum etc) that the entity can tolerate.";
                        }
                        leaf power-rating {
                            type to-be-defined;
                            description "This attribute represents the power chracteristics (peak and mean per power source) of the entity.
                                For an Equipment this is the power consumption.
                                For  a Holder this is the power that can be conveyed.";
                        }
                        leaf humidity-rating {
                            type to-be-defined;
                            description "This attribute represents the humidity characteristics (preferred maximum/minimum, absolute maximum/minimum etc) that the entity can tolerate.";
                        }
                        description "Represents the invariant physical operational boundaries for the equipment/holder type.";
                    }
                    grouping position {
                        leaf relative-position {
                            type to-be-defined;
                            description "none";
                        }
                        description "Represents the invariant relative position of the holder (with respect to some frame of reference in an equipment) or connector on an equipment or pin in a connector.";
                    }
                    grouping spatial-properties-of-type {
                        leaf height {
                            type to-be-defined;
                            description "none";
                        }
                        leaf width {
                            type to-be-defined;
                            description "none";
                        }
                        leaf length {
                            type to-be-defined;
                            description "none";
                        }
                        description "Represents the basic invariant spatial properties of a physical thing.";
                    }
                    grouping swappability {
                        leaf is-hot-swappable {
                            type boolean;
                            default "true";
                            description "none";
                        }
                        description "Represents the degree of field replacement that is possible for the equipment type.";
                    }
                    grouping operator-augmented-equipment-instance {
                        leaf asset-instance-identifier {
                            type string;
                            description "This attribute represents the asset identifier of this instance from the operator's perspective.";
                        }
                        description "Represents the invariant properties of the equipment asset allocated by the operator that define and characterize the type.";
                    }



        /***********************
        * package equipment-pattern-structure
        **********************/ 
            /***********************
            * package object-classes
            **********************/ 
                grouping cable {
                    leaf-list connector {
                        type leafref {
                            path '/core-model:field-replaceable/core-model:connector/core-model:';
                        }
                        min-elements 1;
                        description "A connector that terminates the Cable to support the cable and/or allow signal flow into/out of the Cable.";
                    }
                    leaf manufactured-thing {
                        type leafref {
                            path '/core-model:equipment/core-model:encapsulated-non-fru/core-model:exposed-cable/core-model:manufactured-thing/core-model:';
                        }
                        description "none";
                    }
                    leaf physical-characteristics {
                        type leafref {
                            path '/core-model:equipment/core-model:encapsulated-non-fru/core-model:exposed-cable/core-model:physical-characteristics/core-model:';
                        }
                        description "none";
                    }
                    leaf mechanical-features {
                        type leafref {
                            path '/core-model:equipment/core-model:encapsulated-non-fru/core-model:exposed-cable/core-model:mechanical-features/core-model:';
                        }
                        description "none";
                    }
                    leaf spatial-properties-of-type {
                        type leafref {
                            path '/core-model:equipment/core-model:encapsulated-non-fru/core-model:exposed-cable/core-model:spatial-properties-of-type/core-model:';
                        }
                        description "none";
                    }
                    uses global-class;
                    description "Basic model representing a cable with connectors fitted where the cable is 'short' (e.g.  patch cord, in-station cabling).
                        This is intentionally a very basic representation of a cable. 
                        In a more sophisticated representation cable ends might be represented that then associate to the attached connector. 
                        At this point it is assumed that the basic model is sufficient.";
                }
                grouping connector {
                    leaf connector {
                        type string;
                        description "The Connector that is attached to this Connector so as to join the Equipment/Cable with this Connector to another Equipment/Cable.
                            This may provide physical support and/or allow signal flow.";
                    }
                    leaf-list pin {
                        type leafref {
                            path '/core-model:field-replaceable/core-model:connector/core-model:pin/core-model:';
                        }
                        min-elements 1;
                        description "none";
                    }
                    leaf orientation {
                        type connector-and-pin-orientation;
                        description "none";
                    }
                    leaf manufactured-thing {
                        type leafref {
                            path '/core-model:equipment/core-model:encapsulated-non-fru/core-model:exposed-cable/core-model:manufactured-thing/core-model:';
                        }
                        description "none";
                    }
                    leaf position {
                        type leafref {
                            path '/core-model:field-replaceable/core-model:connector/core-model:position/core-model:';
                        }
                        description "none";
                    }
                    leaf mechanical-features {
                        type leafref {
                            path '/core-model:equipment/core-model:encapsulated-non-fru/core-model:exposed-cable/core-model:mechanical-features/core-model:';
                        }
                        description "none";
                    }
                    leaf pin-layout {
                        type leafref {
                            path '/core-model:field-replaceable/core-model:connector/core-model:pin-layout/core-model:';
                        }
                        description "none";
                    }
                    leaf connector-type {
                        type to-be-defined;
                        description "none";
                    }
                    leaf role {
                        type string;
                        description "The purpose of the Connector in the physical space and the functional space.";
                    }
                    uses local-class;
                    uses group-of-pins;
                    description "Represents a connector that may be fully exposed (e.g. to plug in a cable or on the end of a cable) or partially exposed (e.g. backplane to plug in another piece of equipment such as a module).
                        A physical port on the Equipment. A place where signals produced by the functionality of the Equipment may be accessed.";
                }
                grouping equipment {
                    leaf-list connector {
                        type leafref {
                            path '/core-model:field-replaceable/core-model:connector/core-model:';
                        }
                        description "A connector on the equipment.";
                    }
                    leaf-list contained-holder {
                        type leafref {
                            path '/core-model:field-replaceable/core-model:holder/core-model:';
                        }
                        description "References the Holder in an Equipment that is available to take other Equipments.
                            For example:
                            - Slot in a sub-rack
                            - Slot in a Field Replaceable Unit that can take a small form-factor pluggable.";
                    }
                    leaf addressed-by-holder {
                        type leafref {
                            path '/core-model:field-replaceable/core-model:holder/core-model:';
                        }
                        description "none";
                    }
                    leaf-list encapsulated-non-fru {
                        type leafref {
                            path '/core-model:equipment/core-model:encapsulated-non-fru/core-model:';
                        }
                        description "An Equipment that is part of this Equipment and that is not separately field replaceable (i.e. will be field replaced with this Equipment).";
                    }
                    leaf-list exposed-cable {
                        type leafref {
                            path '/core-model:equipment/core-model:encapsulated-non-fru/core-model:exposed-cable/core-model:';
                        }
                        description "none";
                    }
                    leaf manufactured-thing {
                        type leafref {
                            path '/core-model:equipment/core-model:encapsulated-non-fru/core-model:exposed-cable/core-model:manufactured-thing/core-model:';
                        }
                        description "none";
                    }
                    leaf spatial-properties-of-type {
                        type leafref {
                            path '/core-model:equipment/core-model:encapsulated-non-fru/core-model:exposed-cable/core-model:spatial-properties-of-type/core-model:';
                        }
                        description "none";
                    }
                    leaf mechanical-features {
                        type leafref {
                            path '/core-model:equipment/core-model:encapsulated-non-fru/core-model:exposed-cable/core-model:mechanical-features/core-model:';
                        }
                        description "none";
                    }
                    leaf physical-properties {
                        type leafref {
                            path '/core-model:equipment/core-model:encapsulated-non-fru/core-model:physical-properties/core-model:';
                        }
                        description "none";
                    }
                    leaf function-enablers {
                        type leafref {
                            path '/core-model:equipment/core-model:encapsulated-non-fru/core-model:function-enablers/core-model:';
                        }
                        description "none";
                    }
                    leaf mechanical-functions {
                        type leafref {
                            path '/core-model:equipment/core-model:encapsulated-non-fru/core-model:mechanical-functions/core-model:';
                        }
                        description "none";
                    }
                    leaf physical-characteristics {
                        type leafref {
                            path '/core-model:equipment/core-model:encapsulated-non-fru/core-model:exposed-cable/core-model:physical-characteristics/core-model:';
                        }
                        description "none";
                    }
                    leaf swapability {
                        type leafref {
                            path '/core-model:equipment/core-model:encapsulated-non-fru/core-model:swapability/core-model:';
                        }
                        description "none";
                    }
                    leaf structure {
                        type leafref {
                            path '/core-model:equipment/core-model:encapsulated-non-fru/core-model:structure/core-model:';
                        }
                        description "none";
                    }
                    leaf environmental-rating {
                        type leafref {
                            path '/core-model:equipment/core-model:encapsulated-non-fru/core-model:environmental-rating/core-model:';
                        }
                        description "none";
                    }
                    leaf-list non-fru-support-position {
                        type leafref {
                            path '/core-model:equipment/core-model:encapsulated-non-fru/core-model:non-fru-support-position/core-model:';
                        }
                        description "none";
                    }
                    leaf is-field-replaceable {
                        type boolean;
                        default "true";
                        config false;
                        description "Indicates whether or not the equipment can be removed and replaced 'in the field' (i.e. in a deployment) by normal operations personnel. 
                            ";
                    }
                    leaf-list function-block {
                        type leafref {
                            path '/core-model:equipment/core-model:encapsulated-non-fru/core-model:function-block/core-model:';
                        }
                        description "none";
                    }
                    leaf expected-equipment {
                        type leafref {
                            path '/core-model:equipment/core-model:encapsulated-non-fru/core-model:expected-equipment/core-model:';
                        }
                        description "none";
                    }
                    leaf actual-equipment {
                        type leafref {
                            path '/core-model:equipment/core-model:encapsulated-non-fru/core-model:actual-equipment/core-model:';
                        }
                        description "none";
                    }
                    leaf location {
                        type leafref {
                            path '/core-model:equipment/core-model:encapsulated-non-fru/core-model:location/core-model:';
                        }
                        description "none";
                    }
                    leaf-list foundation-pc {
                        type leafref {
                            path '/core-model:equipment/core-model:encapsulated-non-fru/core-model:foundation-pc/core-model:';
                        }
                        description "Lowest level functional block with 1:1 to equipment.";
                    }
                    uses global-class;
                    description "Represents any relevant physical thing. 
                        Can be either field replaceable or not field replaceable.
                        Note: The model is currently constrained to inside plant.";
                }
                grouping holder {
                    leaf-list connector {
                        type leafref {
                            path '/core-model:field-replaceable/core-model:connector/core-model:';
                        }
                        description "The connector associated with a Holder of an Equipment.
                            May represent connector on a backplane that takes Field Replaceable Units or a connector on a circuit pack that takes an SFP (Small Form-factor Pluggable).";
                    }
                    leaf occupying-fru {
                        type leafref {
                            path '/core-model:equipment/core-model:encapsulated-non-fru/core-model:';
                        }
                        description "The FRU that is occupying the holder. 
                            A holder may be unoccupied. 
                            An FRU may occupy more hat one holder (using or blocking are intentionally not distinguished here).";
                    }
                    leaf spatial-properties-of-type {
                        type leafref {
                            path '/core-model:equipment/core-model:encapsulated-non-fru/core-model:exposed-cable/core-model:spatial-properties-of-type/core-model:';
                        }
                        description "none";
                    }
                    leaf-list holder-monitor {
                        type leafref {
                            path '/core-model:field-replaceable/core-model:holder/core-model:holder-monitor/core-model:';
                        }
                        description "none";
                    }
                    container holder-location {
                        uses address;
                        description "none";
                    }
                    leaf position {
                        type leafref {
                            path '/core-model:field-replaceable/core-model:connector/core-model:position/core-model:';
                        }
                        description "none";
                    }
                    leaf holder-structure {
                        type leafref {
                            path '/core-model:field-replaceable/core-model:holder/core-model:holder-structure/core-model:';
                        }
                        description "none";
                    }
                    leaf environmental-rating {
                        type leafref {
                            path '/core-model:equipment/core-model:encapsulated-non-fru/core-model:environmental-rating/core-model:';
                        }
                        description "none";
                    }
                    leaf-list supported-equipment-type {
                        type leafref {
                            path '/core-model:field-replaceable/core-model:holder/core-model:supported-equipment-type/core-model:';
                        }
                        min-elements 1;
                        description "An Equipment type that the Holder can accommodate (is compatible with).";
                    }
                    leaf expected-holder {
                        type leafref {
                            path '/core-model:field-replaceable/core-model:holder/core-model:expected-holder/core-model:';
                        }
                        description "none";
                    }
                    leaf actual-holder {
                        type leafref {
                            path '/core-model:field-replaceable/core-model:holder/core-model:actual-holder/core-model:';
                        }
                        description "none";
                    }
                    uses local-class;
                    description "Represents a space in an equipment in which another equipment can be fitted in the field.";
                }

            /***********************
            * package data-types
            **********************/ 
                typedef ConnectorAndPinOrientation {
                    type identityref {
                        base connector-and-pin-orientation;
                    }
                    description "Most connector schems are asymmetric such that there are two orientations of the connector where a mating is only possible between two connectors of different orientations. 
                        A multi-pin connector may have a mix of pin orientations. In this case, it is expected that the dominant orientation of pin is chosen for the connector orientation.";
                }
                typedef EquipmentCategory {
                    type identityref {
                        base equipment-category;
                    }
                    description "The form of equipment.";
                }
                typedef HolderCategory {
                    type identityref {
                        base holder-category;
                    }
                    description "The form of holder.";
                }


        /***********************
        * package equipment-specification
        **********************/ 
            /***********************
            * package object-classes
            **********************/ 
                grouping support-constraints {
                    leaf-list constrained-supported-non-fru-type {
                        type leafref {
                            path '/core-model:equipment/core-model:encapsulated-non-fru/core-model:non-fru-support-position/core-model:supported-non-fru-type/core-model:';
                        }
                        description "none";
                    }
                    leaf-list constrained-supported-fru-type {
                        type leafref {
                            path '/core-model:field-replaceable/core-model:holder/core-model:supported-equipment-type/core-model:';
                        }
                        description "none";
                    }
                    description "Rules related to how both non-FRU and FRU presence restricts the potential for additional equipments to be installed.
                        An FRU type installed in one holder may limit the FRU types that can be installed in another holder etc.";
                }
                grouping supported-non-fru-type {
                    leaf non-fru-details {
                        type leafref {
                            path '/core-model:equipment/core-model:encapsulated-non-fru/core-model:';
                        }
                        description "none";
                    }
                    leaf-list blocked-non-fru-position {
                        type leafref {
                            path '/core-model:equipment/core-model:encapsulated-non-fru/core-model:non-fru-support-position/core-model:';
                        }
                        min-elements 1;
                        description "none";
                    }
                    leaf-list support-constraints {
                        type leafref {
                            path '/core-model:support-constraints/core-model:';
                        }
                        description "none";
                    }
                    description "The non-FRU equipment types supported by the non-FRU support position.";
                }
                grouping non-fru-support-position {
                    leaf-list supported-non-fru-type {
                        type leafref {
                            path '/core-model:equipment/core-model:encapsulated-non-fru/core-model:non-fru-support-position/core-model:supported-non-fru-type/core-model:';
                        }
                        min-elements 1;
                        description "none";
                    }
                    description "Equivalent to the holder for the FRU, represents in the specification a place where one or more types of non-FRU could be present. 
                        Unlike the holder what is present is fixed whilst the equipment is in the field.";
                }
                grouping supported-equipment-type {
                    leaf fru-details {
                        type leafref {
                            path '/core-model:equipment/core-model:encapsulated-non-fru/core-model:';
                        }
                        description "none";
                    }
                    leaf-list support-constraints {
                        type leafref {
                            path '/core-model:support-constraints/core-model:';
                        }
                        description "none";
                    }
                    leaf-list holder {
                        type leafref {
                            path '/core-model:field-replaceable/core-model:holder/core-model:';
                        }
                        min-elements 1;
                        description "none";
                    }
                    description "The FRU equipment types supported by the holder.";
                }


        /***********************
        * package expected-and-actual
        **********************/ 
            /***********************
            * package object-classes
            **********************/ 
                grouping actual-holder {
                    description "A holder in the ActualEquipment.";
                }
                grouping expected-holder {
                    description "A definition of a holder expected in the ActualEquipment (i.e. an ActualHolder) as part of the constraints provided by the ExpectedEquipment.";
                }
                grouping actual-equipment {
                    description "The equipment that is actually present in the physical network.
                        It will expose all dynamic properties and some critical static properties.";
                }
                grouping expected-equipment {
                    description "A definition of the restrictions on the equipment that is expected to be present in the physical network at a particular 'place'.
                        The expected equipment will state the type and may constrain any other invariant properties. 
                        It may also provide desired ranges for dynamic properties.";
                }


        /***********************
        * package connector-and-pin
        **********************/ 
            /***********************
            * package object-classes
            **********************/ 
                grouping pin {
                    leaf position {
                        type leafref {
                            path '/core-model:field-replaceable/core-model:connector/core-model:position/core-model:';
                        }
                        description "none";
                    }
                    leaf orientation {
                        type connector-and-pin-orientation;
                        description "none";
                    }
                    description "An individual physical connection point (male or female) that is not relevantly divisible.
                        May be capable of carrying electrical or optical signals. 
                        A pin normally has only one wire/fiber strand attached. 
                        It may have more than one wire/fiber attached but is such that the attachment forms a physical merge (all attached things receive exactly the same signal and any inputs to the pin are electrically/optically merged).";
                }
                grouping pin-group {
                    leaf-list pin {
                        type leafref {
                            path '/core-model:field-replaceable/core-model:connector/core-model:pin/core-model:';
                        }
                        min-elements 1;
                        description "none";
                    }
                    uses access-port;
                    uses group-of-pins;
                    description "A group of pins that together provide signal group where any one pin removed from the group will prevent the signals of the signal group from flowing successfully.";
                }
                grouping pin-layout {
                    leaf-list position {
                        type leafref {
                            path '/core-model:field-replaceable/core-model:connector/core-model:position/core-model:';
                        }
                        min-elements 1;
                        description "none";
                    }
                    description "The structuring of pins in a connector.";
                }
                grouping access-port {
                    description "A conceptual access for a group of signals (where that group of signals cannot be separated).";
                }
                grouping signal-ref-pt {
                    leaf ltp {
                        type leafref {
                            path '/core-model:network-control-domain/core-model:network-element/core-model:ltp/core-model:';
                        }
                        description "none";
                    }
                    leaf-list elemental-signals {
                        type leafref {
                            path '/core-model:elemental-signals/core-model:';
                        }
                        min-elements 1;
                        description "none";
                    }
                    description "A single coherent signal as processed by a single LTP.";
                }
                grouping signal-ref-pt-group {
                    leaf pin-group {
                        type leafref {
                            path '/core-model:pin-group/core-model:';
                        }
                        description "none";
                    }
                    leaf-list signal-ref-pt {
                        type leafref {
                            path '/core-model:signal-ref-pt/core-model:';
                        }
                        min-elements 1;
                        description "none";
                    }
                    uses access-port;
                    description "A physical indivisible group of signals.";
                }
                grouping elemental-signals {
                    leaf-list pin {
                        type leafref {
                            path '/core-model:field-replaceable/core-model:connector/core-model:pin/core-model:';
                        }
                        min-elements 1;
                        description "none";
                    }
                    description "The elemental (sub-atomic) parts of an 'indivisible' signal where processing in the LTP is required to extract the elemental signals.";
                }
                grouping group-of-pins {
                    description "A group of pins from one or more connectors relevant for some purpose.";
                }


        /***********************
        * package equipment-to-function
        **********************/ 
            /***********************
            * package object-classes
            **********************/ 
                grouping aggregate-function {
                    leaf-list atomic-function {
                        type leafref {
                            path '/core-model:equipment/core-model:encapsulated-non-fru/core-model:function-block/core-model:atomic-function/core-model:';
                        }
                        description "none";
                    }
                    leaf-list function-block {
                        type leafref {
                            path '/core-model:equipment/core-model:encapsulated-non-fru/core-model:function-block/core-model:';
                        }
                        description "none";
                    }
                    leaf-list atomic-function-view {
                        type leafref {
                            path '/core-model:equipment/core-model:encapsulated-non-fru/core-model:function-block/core-model:atomic-function/core-model:';
                        }
                        description "none";
                    }
                    description "Represents some assembly of atomic functions that can be considered as useful from some perspective. Can be viewed as one or more functional blocks (essential leading to a recursive cycle of Block --> Atomic --> Aggregate --> Block). 
                        Each of the functional entities in the model is a view of a single AggregateFunction.";
                }
                grouping atomic-function {
                    leaf-list aggregate-function {
                        type leafref {
                            path '/core-model:aggregate-function/core-model:';
                        }
                        description "none";
                    }
                    description "Represents the micro-function that is the largest function of the functional block that will not need to be subdivided when forming the relevant abstract views (i.e., it can just be assembled).";
                }
                grouping function-block {
                    leaf-list atomic-function {
                        type leafref {
                            path '/core-model:equipment/core-model:encapsulated-non-fru/core-model:function-block/core-model:atomic-function/core-model:';
                        }
                        description "none";
                    }
                    leaf-list equipment {
                        type leafref {
                            path '/core-model:equipment/core-model:encapsulated-non-fru/core-model:';
                        }
                        description "none";
                    }
                    description "Represents the chunks of base functionality provided by the equipment.
                        The chunks of base functionality are likely to relate to the hardware layout and be quite distinct from the functions of the familiar abstract representation.
                        The functions are necessarily abstract and, to a degree, virtualized.";
                }
                grouping resilient-function-block {
                    leaf-list atomic-function {
                        type leafref {
                            path '/core-model:equipment/core-model:encapsulated-non-fru/core-model:function-block/core-model:atomic-function/core-model:';
                        }
                        description "none";
                    }
                    description "Represents the functions emergent from a function protection process.
                        The emergent functions are necessarily significantly virtualized.";
                }
                grouping resilience-selector {
                    leaf resilient-function-block {
                        type leafref {
                            path '/core-model:resilience-selector/core-model:resilient-function-block/core-model:';
                        }
                        description "none";
                    }
                    leaf-list function-block {
                        type leafref {
                            path '/core-model:equipment/core-model:encapsulated-non-fru/core-model:function-block/core-model:';
                        }
                        min-elements 2;
                        description "none";
                    }
                    description "Represents the ability to select capability from two or more identical FunctionalBlocks so as to give rise to an equivalent emergent resilient function.";
                }



    /***********************
    * package core-specification-model
    **********************/ 
        /***********************
        * package fc-capability
        **********************/ 
            /***********************
            * package object-classes
            **********************/ 
                /***********************
                * package fc-capability-core
                **********************/ 
                    grouping configuration-and-switch-controller-spec {
                        leaf-list switch-control-rule {
                            type leafref {
                                path '/core-model:configuration-group-spec/core-model:forwarding-spec/core-model:casc-spec/core-model:switch-control-rule/core-model:';
                            }
                            min-elements 1;
                            description "none";
                        }
                        leaf-list ingress-switch-selection {
                            type string;
                            description "none";
                        }
                        leaf-list egress-switch-selection {
                            type string;
                            description "none";
                        }
                        uses global-class;
                        description "The spec of a ConfigurationAndSwitchController.";
                    }
                    grouping layer-protocol-parameter-spec {
                        description "Offers the opportunity to define a list layer-protocol related parameters. 
                            Used to specify the extension a class. ";
                    }
                    grouping egress-port-set {
                        uses local-class;
                        description "The grouping of FC egress ports that have the same behavior and relationship to the switch etc.
                            Will carry rules for the grouping.";
                    }
                    grouping forwarding-spec {
                        leaf-list multi-switched-uni-flow {
                            type leafref {
                                path '/core-model:configuration-group-spec/core-model:forwarding-spec/core-model:multi-switched-uni-flow/core-model:';
                            }
                            min-elements 1;
                            description "none";
                        }
                        leaf-list casc-spec {
                            type leafref {
                                path '/core-model:configuration-group-spec/core-model:forwarding-spec/core-model:casc-spec/core-model:';
                            }
                            description "none";
                        }
                        leaf-list port-set-spec {
                            type leafref {
                                path '/core-model:configuration-group-spec/core-model:forwarding-spec/core-model:port-set-spec/core-model:';
                            }
                            min-elements 1;
                            description "none";
                        }
                        leaf configuration-group-spec-spec {
                            type leafref {
                                path '/core-model:configuration-group-spec/core-model:';
                            }
                            description "none";
                        }
                        leaf ltp-association-rule {
                            type leafref {
                                path '/core-model:configuration-group-spec/core-model:forwarding-spec/core-model:ltp-association-rule/core-model:';
                            }
                            description "none";
                        }
                        leaf-list layer-protocol-parameter-spec {
                            type leafref {
                                path '/core-model:layer-protocol-parameter-spec/core-model:';
                            }
                            description "none";
                        }
                        leaf-list subordinate-forwarding {
                            type leafref {
                                path '/core-model:configuration-group-spec/core-model:forwarding-spec/core-model:subordinate-forwarding/core-model:';
                            }
                            description "none";
                        }
                        leaf-list component-ltp {
                            type leafref {
                                path '/core-model:configuration-group-spec/core-model:forwarding-spec/core-model:component-ltp/core-model:';
                            }
                            description "none";
                        }
                        leaf spec-target-class {
                            type metaclass-class-name;
                            description "
                                range of type : Link, ForwardingConstruct";
                        }
                        uses global-class;
                        description "The overall spec for the forwarding entity.";
                    }
                    grouping ingress-port-set {
                        uses local-class;
                        description "The grouping of FC ingress ports that have the same behavior and relationship to the switch etc.
                            Will carry rules for the grouping.";
                    }
                    grouping multi-switched-uni-flow {
                        leaf-list ingress-port-set {
                            type leafref {
                                path '/core-model:configuration-group-spec/core-model:forwarding-spec/core-model:multi-switched-uni-flow/core-model:ingress-port-set/core-model:';
                            }
                            min-elements 1;
                            description "none";
                        }
                        leaf-list egress-port-set {
                            type leafref {
                                path '/core-model:configuration-group-spec/core-model:forwarding-spec/core-model:multi-switched-uni-flow/core-model:egress-port-set/core-model:';
                            }
                            min-elements 1;
                            description "none";
                        }
                        leaf casc {
                            type leafref {
                                path '/core-model:configuration-group-spec/core-model:forwarding-spec/core-model:casc-spec/core-model:';
                            }
                            description "none";
                        }
                        leaf ingress-fc-port-set {
                            type leafref {
                                path '/core-model:configuration-group-spec/core-model:forwarding-spec/core-model:multi-switched-uni-flow/core-model:ingress-port-set/core-model:';
                            }
                            description "none";
                        }
                        leaf egress-fc-port-set {
                            type leafref {
                                path '/core-model:configuration-group-spec/core-model:forwarding-spec/core-model:multi-switched-uni-flow/core-model:egress-port-set/core-model:';
                            }
                            description "none";
                        }
                        leaf layer-protocol-parameter-spec {
                            type leafref {
                                path '/core-model:layer-protocol-parameter-spec/core-model:';
                            }
                            description "none";
                        }
                        uses local-class;
                        description "A switched unidirectional forwarding element that can take one or more inputs and switch to one or more outputs.
                            The switch can also be open (high impedance).";
                    }
                    grouping port-set-spec {
                        leaf-list ingress-port-set {
                            type leafref {
                                path '/core-model:configuration-group-spec/core-model:forwarding-spec/core-model:multi-switched-uni-flow/core-model:ingress-port-set/core-model:';
                            }
                            description "none";
                        }
                        leaf-list egress-port-set {
                            type leafref {
                                path '/core-model:configuration-group-spec/core-model:forwarding-spec/core-model:multi-switched-uni-flow/core-model:egress-port-set/core-model:';
                            }
                            description "none";
                        }
                        leaf ltp-association-rule {
                            type leafref {
                                path '/core-model:configuration-group-spec/core-model:forwarding-spec/core-model:ltp-association-rule/core-model:';
                            }
                            description "none";
                        }
                        leaf role {
                            type string;
                            default "true";
                            description "Role of the port in the context of the ForwardingSpec.";
                        }
                        leaf layer-protocol-parameter-spec {
                            type leafref {
                                path '/core-model:layer-protocol-parameter-spec/core-model:';
                            }
                            description "none";
                        }
                        leaf is-internal-port {
                            type boolean;
                            config false;
                            description "The FcPort is not exposed and cannot have associated LTPs.
                                This form of FcPort is used to enable chaining of FcSwitches or FcRoutes in complex network protection scenarios.";
                        }
                        leaf client-side-of-ltp {
                            type leafref {
                                path '/core-model:configuration-group-spec/core-model:forwarding-spec/core-model:component-ltp/core-model:';
                            }
                            description "none";
                        }
                        leaf server-side-of-ltp {
                            type leafref {
                                path '/core-model:configuration-group-spec/core-model:forwarding-spec/core-model:component-ltp/core-model:';
                            }
                            description "none";
                        }
                        uses local-class;
                        description "The specification a set of equivalent port of the forwarding entity.";
                    }

                /***********************
                * package fc-capability-additional
                **********************/ 
                    grouping component-ltp {
                        description "none";
                    }
                    grouping configuration-group-spec {
                        leaf casc {
                            type leafref {
                                path '/core-model:configuration-group-spec/core-model:forwarding-spec/core-model:casc-spec/core-model:';
                            }
                            description "none";
                        }
                        leaf-list forwarding-spec {
                            type leafref {
                                path '/core-model:configuration-group-spec/core-model:forwarding-spec/core-model:';
                            }
                            min-elements 1;
                            description "none";
                        }
                        leaf ltp-association-rule {
                            type leafref {
                                path '/core-model:configuration-group-spec/core-model:forwarding-spec/core-model:ltp-association-rule/core-model:';
                            }
                            description "none";
                        }
                        uses global-class;
                        description "The specification of the grouping rules for a particular configuration of FCs and CASCs.";
                    }
                    grouping control-rule {
                        uses local-class;
                        description "A rule describes the bounds of the behavior of a CASC.";
                    }
                    grouping subordinate-forwarding {
                        description "none";
                    }
                    grouping ltp-association-rule {
                        uses local-class;
                        description "Rules for the association from the port spec to LTPs identifying restrictions of use.";
                    }



        /***********************
        * package forwarding-domain-and-link-capability
        **********************/ 
            /***********************
            * package object-classes
            **********************/ 
                grouping fd-and-link-rule {
                    leaf rule-type {
                        type rule-type;
                        description "Indicates how to interpret the rule statements.";
                    }
                    leaf forwarding-rule {
                        type forwarding-rule;
                        description "none";
                    }
                    leaf-list complex-rule-qualifier {
                        type to-be-defined;
                        description "complexRuleQualifier is used to modulate the rule.
                            complexRuleQualifier covers case such as same channel but can reference any property of the FD, of the associated LTP and of the FC instance to be created.
                            Qualifier should be capable of expressing rule interaction.
                            Provides restrictions (such as same channel).
                            Note: May be better to have a same index/any index explicit rule.
                            Could have 'property=x' valueEquation=same, increment, etc.'";
                    }
                    leaf fc-spec {
                        type to-be-defined;
                        description "Indicates the type(s) of FC to which the rule applies.";
                    }
                    list fc-port-role {
                        uses port-role-rule;
                        description "Indicates the port role to which the rule applies. 
                            If an FD carries a port role that role applies also to the associated Link rules.
                            fcPortRole corresponded to role defined in the FcSpec. This is a list with rule opportunity. No port role statement means all port roles are allowed.";
                    }
                    leaf-list fc-port-direction {
                        type port-direction;
                        description "fcPortDirection is a list of FcPortDirection.";
                    }
                    leaf override-priority {
                        type uint64;
                        description "overridePriority allows for one rule set to override another.";
                    }
                    leaf signal-property {
                        type string;
                        description "none";
                    }
                    list fc-spec-reference-class-ref {
                        if-feature spectargetclass-forwardingconstruct;
                        uses metaclass-class;
                        description "none";
                    }
                    description "Set of 'AND' rules related to creation of FCs across the FD/Link (i.e., all rules have to be met for the FC creation to be allowed).
                        Embedded conditions all have to be met and hence are AND. Elements of the list attributes are ORs.
                        Absence fcSpec NOT valid for FORWARDING rules (only valid for cost/risk etc. rules).
                        Absence of FcPortRole means all roles for referenced spec.
                        Absence of direction means all directions.";
                }
                grouping fd-and-link-rule-set {
                    leaf-list fd-rule {
                        type leafref {
                            path '/core-model:fd-and-link-rule/core-model:';
                        }
                        min-elements 1;
                        description "none";
                    }
                    leaf is-rule-only {
                        type boolean;
                        description "Indicates that the FD is only carrying rules and that FC creation is the FD is NOT allowed.";
                    }
                    description "Set of 'OR' rules related to creation of FCs across the FD/Link (i.e. only one of the rules have to be met for the FC creation to be allowed).
                        Absence of RuleSet means 'Any', i.e. all points, all FcTypes etc.
                        Presence of RuleSet means possibilities must all be defined by rules
                        Absence of forwardingRule means no explicit stated possibilities.
                        No capacity statement means no capacity restrictions.
                        ";
                }

            /***********************
            * package type-definitions
            **********************/ 
                identity PORT_DIRECTION {
                    description "none";
                }
                identity PORT_DIRECTION_BIDIRECTIONAL {
                    base port-direction;
                    description "The Port has both an INPUT flow and an OUTPUT flow defined.";
                }
                identity PORT_DIRECTION_INPUT {
                    base port-direction;
                    description "The Port only has definition for a flow into the Forwarding entity (i.e. an ingress flow).";
                }
                identity PORT_DIRECTION_OUTPUT {
                    base port-direction;
                    description "The Port only has definition for a flow out of the Forwarding entity (i.e. an egress flow).";
                }
                identity PORT_DIRECTION_UNIDENTIFIED_OR_UNKNOWN {
                    base port-direction;
                    description "Not a normal state. The system is unable to determine the correct value.";
                }
                identity PORT_DIRECTION_OMNIDIRECTIONAL {
                    base port-direction;
                    description "none";
                }
                identity FORWARDING_DIRECTION {
                    description "none";
                }
                identity FORWARDING_DIRECTION_BIDIRECTIONAL {
                    base forwarding-direction;
                    description "The Forwarding entity supports both BIDIRECTIONAL flows at all Ports (i.e. all Ports have both an INPUT flow and an OUTPUT flow defined).";
                }
                identity FORWARDING_DIRECTION_UNIDIRECTIONAL {
                    base forwarding-direction;
                    description "The Forwarding entity has Ports that are either INPUT or OUTPUT. It has no BIDIRECTIONAL Ports.";
                }
                identity FORWARDING_DIRECTION_UNDEFINED_OR_UNKNOWN {
                    base forwarding-direction;
                    description "Not a normal state. The system is unable to determine the correct value.";
                }
                identity FORWARDING_DIRECTION_OMNIDIRECTIONAL {
                    base forwarding-direction;
                    description "none";
                }
                identity TERMINATION_DIRECTION {
                    description "none";
                }
                identity TERMINATION_DIRECTION_BIDIRECTIONAL {
                    base termination-direction;
                    description "A Termination with both SINK and SOURCE flows.";
                }
                identity TERMINATION_DIRECTION_SINK {
                    base termination-direction;
                    description "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base termination-direction;
                    description "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base termination-direction;
                    description "Not a normal state. The system is unable to determine the correct value.";
                }
                identity EXTENDED_TERMINATION_DIRECTION {
                    description "none";
                }
                identity EXTENDED_TERMINATION_DIRECTION_CONTRA_DIRECTION_SINK {
                    base extended-termination-direction;
                    description "The essential flow of the Termination entity is SINK (i.e. up the layer stack) but the INPUT flow of the Termination entity was provided by a SOURCE OUTPUT or taken from a SOURCE INPUT (duplicating the input signal) hence reversing the flow orientation from down the layer stack to up the layer stack.";
                }
                identity EXTENDED_TERMINATION_DIRECTION_CONTRA_DIRECTION_SOURCE {
                    base extended-termination-direction;
                    description "The essential flow of the Termination entity is SOURCE (i.e. down the layer stack) but the OUTPUT flow of the Termination entity was fed to (and replaces) a SINK OUTPUT or was fed to a SINK INPUT (replacing the normal flow) hence reversing the flow orientation from down the layer stack to up the layer stack.";
                }
                identity TERMINATION_STATE {
                    description "none";
                }
                identity TERMINATION_STATE_LP_CAN_NEVER_TERMINATE {
                    base termination-state;
                    description "A non-flexible case that can never be terminated.";
                }
                identity TERMINATION_STATE_LP_NOT_TERMINATED {
                    base termination-state;
                    description "A flexible termination that can terminate but is currently not terminated.";
                }
                identity TERMINATION_STATE_TERMINATED_SERVER_TO_CLIENT_FLOW {
                    base termination-state;
                    description "A flexible termination that is currently terminated for server to client flow only.";
                }
                identity TERMINATION_STATE_TERMINATED_CLIENT_TO_SERVER_FLOW {
                    base termination-state;
                    description "A flexible termination that is currently terminated for client to server flow only.";
                }
                identity TERMINATION_STATE_TERMINATED_BIDIRECTIONAL {
                    base termination-state;
                    description "A flexible termination that is currently terminated in both directions of flow.";
                }
                identity TERMINATION_STATE_LP_PERMENANTLY_TERMINATED {
                    base termination-state;
                    description "A non-flexible termination that is always terminated (in both directions of flow for a bidirectional case and in the one direction of flow for both unidirectional cases).";
                }
                identity TERMINATION_STATE_TERMINATION_STATE_UNKNOWN {
                    base termination-state;
                    description "There TerminationState cannot be determined.";
                }
                identity PROTECTION_REASON {
                    description "none";
                }
                identity PROTECTION_REASON_WAIT_TO_REVERT {
                    base protection-reason;
                    description "The resource is selected as control is waiting to restore to a preferred resource.";
                }
                identity PROTECTION_REASON_SIGNAL_DEGRADE {
                    base protection-reason;
                    description "The resource is selected as the best preferred resource is in signal degrade.";
                }
                identity PROTECTION_REASON_SIGNAL_FAIL {
                    base protection-reason;
                    description "The resource is selected as the best preferred resource is in signal fail.";
                }
                identity ROUTE_SELECTION_CONTROL {
                    description "none";
                }
                identity ROUTE_SELECTION_CONTROL_LOCK_OUT {
                    base route-selection-control;
                    description "The resource is configured to temporarily not be available for use in the protection scheme(s) it is part of.
                        This overrides all other protection control states including forced.
                        If the item is locked out, then it cannot be used under any circumstances.
                        Note: Only relevant when part of a protection scheme.
                        Note: if a protection process that has a relationship to the item (i.e. is one of the options the protection process may choose) is deactivated by being isFrozen = true) then the lockout request will be rejected. ";
                }
                identity ROUTE_SELECTION_REASON {
                    description "none";
                }
                identity SWITCH_CONTROL {
                    description "none";
                }
                identity SWITCH_CONTROL_NORMAL {
                    base switch-control;
                    description "No administrative control applied to the switch.";
                }
                identity SWITCH_CONTROL_MANUAL {
                    base switch-control;
                    description "Resource temporarily chosen by control configuration where the resource is not the preferred resource.
                        Preferred resource has highest priority.
                        Temporarily overrides reversion.
                        If this resource fails, it will switch to best available resource. 
                        If resource selected is shared and another FC requires the resource, then the selection control will change to Normal and switch to best available based upon normal rules.
                        Cannot manually switch a Forced switch, cannot remove a forced switch, cannot switch to a locked out item and will be rejected if the protection process is deactivated by being Freeze = true).
                        A manual switch/route that is selecting an FcPort, LTP, FC, Link or Route that is subsequently set to LOCK_OUT will have the manual removed (changed to NORMAL) and will switch away from the  FcPort with LOCK_OUT to best available based upon normal rules.
                        A manual switch that is selecting an FcPort that is subsequently selected by a Forced switch will be restored to normal operation and the manual will be removed.
                        A manual switch/route that is selecting an FcPort, LTP, FC, Link or Route that is subsequently manual selected by another switch/route  will have the manual removed and will switch away from the FcPort.
                        Can be returned to NORMAL by configuration action.";
                }
                identity SWITCH_CONTROL_FORCED {
                    base switch-control;
                    description "Resource temporarily chosen by control configuration where the resource is not the preferred resource.
                        Preferred resource has highest priority.
                        Temporarily overrides reversion.
                        If this resource fails it will NOT switch. 
                        If resource selected is shared and another FC requires the resource through a FORCE on that FC and the FC is of a higher FcPriority then the selection control on this FC will change to NORMAL and switch to best available based upon normal rules.
                        If the resource selected is then set to LOCK_OUT then the selection control will change to NORMAL and switch to best available based upon normal rules.
                        Can be returned to NORMAL by configuration action.";
                }
                identity SWITCH_STATE_REASON {
                    description "none";
                }
                identity REVERSION_MODE {
                    description "none";
                }
                identity REVERSION_MODE_REVERTIVE {
                    base reversion-mode;
                    description "An FC switched to a lower priority (non-preferred) resource will revert to a higher priority (preferred) resource when that recovers (potentially after some hold-off time).";
                }
                identity REVERSION_MODE_NON-REVERTIVE {
                    base reversion-mode;
                    description "An FC switched to a lower priority (non-preferred) resource will not revert to a higher priority (preferred) resource when that recovers.";
                }
                identity RESILIENCE_CONTROL {
                    description "none";
                }
                identity RESILIENCE_CONTROL_QUIESCENT {
                    base resilience-control;
                    description "none";
                }
                identity RESILIENCE_CONTROL_RESTORING {
                    base resilience-control;
                    description "none";
                }
                identity RESILIENCE_CONTROL_RECOVERY_FAILED {
                    base resilience-control;
                    description "none";
                }
                identity RESILIENCE_CONTROL_UNKNOWN {
                    base resilience-control;
                    description "none";
                }
                identity RUN_MODE {
                    description "none";
                }
                identity RUN_MODE_FREE_RUN {
                    base run-mode;
                    description "The ckock is not synchronized to another clock.";
                }
                identity RUN_MODE_LOCKED {
                    base run-mode;
                    description "The clock is synchronised to another clock.";
                }
                identity RUN_MODE_HOLD_OVER {
                    base run-mode;
                    description "The clock was previously synchonised to another clock but that timing input has been lost.
                        The clock is set to the last known synchronization.";
                }
                identity OPERATIONAL_STATE {
                    description "none";
                }
                identity OPERATIONAL_STATE_DISABLED {
                    base operational-state;
                    description "The resource is unable to meet the SLA of the user of the resource. 
                        If no (explicit) SLA is defined the resource is disabled if it is totally inoperable and unable to provide service to the user.";
                }
                identity OPERATIONAL_STATE_ENABLED {
                    base operational-state;
                    description "The resource is partially or fully operable and available for use.";
                }
                identity ADMINISTRATIVE_STATE {
                    description "none";
                }
                identity ADMINISTRATIVE_STATE_LOCKED {
                    base administrative-state;
                    description "Users are administratively prohibited from making use of the resource.";
                }
                identity ADMINISTRATIVE_STATE_UNLOCKED {
                    base administrative-state;
                    description "Users are allowed to use the resource.";
                }
                identity ADMINISTRATIVE_STATE_SHUTTING_DOWN {
                    base administrative-state;
                    description "The entity is administratively restricted to existing instances of use only. There may be specific actions to remove existing uses. No new instances of use can be enabled.
                        The resource automatically transitions to “locked” when the last user quits. 
                        The administrative state is not visible in the client context. 
                        The lifecycle state “pending removal” should be used to indicate to the client that the provider intends to remove the resource.";
                }
                identity ADMINISTRATIVE_CONTROL {
                    description "none";
                }
                identity ADMINISTRATIVE_CONTROL_UNLOCK {
                    base administrative-control;
                    description "The intention is for the entity to become unlocked.
                        The entity may already be UNLOCKED.";
                }
                identity ADMINISTRATIVE_CONTROL_LOCK_PASSIVE {
                    base administrative-control;
                    description "The intention is for the entity to become locked but no effort is expected to move to the Locked state (the state will be achieved once all users stop using the resource). 
                        The entity may be LOCKED.";
                }
                identity ADMINISTRATIVE_CONTROL_LOCK_ACTIVE {
                    base administrative-control;
                    description "The intention is for the entity to become locked and it is expected that effort will be made to move to the Locked state (users will be actively removed). 
                        The entity may already be LOCKED.";
                }
                identity ADMINISTRATIVE_CONTROL_LOCK_IMMEDIATE {
                    base administrative-control;
                    description "The intention is for the entity to become locked and it is expected to move to the Locked state immediately (users will be force removed). 
                        The entity may already be LOCKED.";
                }
                identity ADMINISTRATIVE_CONTROL_QUIESCENT {
                    base administrative-control;
                    description "The administrative state is at a stable value (LOCKED/UNLOCKED) and no action is being taken.";
                }
                identity LIFECYCLE_STATE {
                    description "none";
                }
                identity LIFECYCLE_STATE_PLANNED {
                    base lifecycle-state;
                    description "The resource is planned but is not present in the network.
                        Should include a 'time' when the resources are expected to be installed.";
                }
                identity LIFECYCLE_STATE_POTENTIAL_AVAILABLE {
                    base lifecycle-state;
                    description "The supporting resources are present in the network but are shared with other clients; or require further configuration before they can be used; or both.
                        (1) When a potential resource is configured and allocated to a client it is moved to the INSTALLED state for that client.
                        (2) If the potential resource has been consumed (e.g. allocated to another client) it is moved to the POTENTIAL BUSY state for all other clients.";
                }
                identity LIFECYCLE_STATE_POTENTIAL_BUSY {
                    base lifecycle-state;
                    description "The supporting resources are present in the network but have been allocated to other clients.";
                }
                identity LIFECYCLE_STATE_INSTALLED {
                    base lifecycle-state;
                    description "The resource is present in the network and is capable of providing the service.";
                }
                identity LIFECYCLE_STATE_PENDING_REMOVAL {
                    base lifecycle-state;
                    description "The resource has been marked for removal.  Should include a “time” when the resources are expected to be removed.";
                }
                identity BLOCK_DIRECTION {
                    description "none";
                }
                identity BLOCK_DIRECTION_NO_BLOCK {
                    base block-direction;
                    description "none";
                }
                identity ACTION_VERBS {
                    description "none";
                }
                identity ACTION_VERBS_CREATE_POST_ADD {
                    base action-verbs;
                    description "none";
                }
                identity ACTION_VERBS_SET_UPDATE_PUT_MODIFY_WRITE_ADD {
                    base action-verbs;
                    description "none";
                }
                identity ACTION_VERBS_GET_READ {
                    base action-verbs;
                    description "none";
                }
                identity ACTION_VERBS_DELETE_REMOVE {
                    base action-verbs;
                    description "none";
                }
                identity ACTIVITY_DIRECTIVE {
                    description "none";
                }
                identity ACTIVITY_DIRECTIVE_STRUCTURE_IS_NOT {
                    base activity-directive;
                    description "none";
                }
                identity ACTIVITY_DIRECTIVE_NEW_STRUCTURE_AND_VALUES {
                    base activity-directive;
                    description "none";
                }
                identity ACTIVITY_DIRECTIVE_INCREMENTAL_STRUCTURE_AND_VALUES {
                    base activity-directive;
                    description "none";
                }
                identity ACTIVITY_DIRECTIVE_ONLY_VALUES_IN_EXISTING_STRUCTURE {
                    base activity-directive;
                    description "none";
                }
                identity ACTIVITY_DIRECTIVE_DEFINED_BY_VERB {
                    base activity-directive;
                    description "none";
                }
                identity ACTION_EFFORT {
                    description "none";
                }
                identity ACTION_EFFORT_BEST_EFFORT {
                    base action-effort;
                    description "none";
                }
                identity ACTION_EFFORT_EXACT_MATCH {
                    base action-effort;
                    description "none";
                }
                identity PAUSE_RESUME_RULE {
                    description "none";
                }
                identity PAUSE_RESUME_RULE_NO_PAUSE_POSSIBLE {
                    base pause-resume-rule;
                    description "none";
                }
                identity CONNECTOR_AND_PIN_ORIENTATION {
                    description "none";
                }
                identity CONNECTOR_AND_PIN_ORIENTATION_MALE {
                    base connector-and-pin-orientation;
                    description "The connecting elements are dominantly protrusions.";
                }
                identity CONNECTOR_AND_PIN_ORIENTATION_FEMALE {
                    base connector-and-pin-orientation;
                    description "The connecting elements are dominantly indentations.";
                }
                identity CONNECTOR_AND_PIN_ORIENTATION_SYMMETRIC_NEUTRAL {
                    base connector-and-pin-orientation;
                    description "The pin (and housing) orientation combination is such that it is symmetric so a connector is compatible with itself.
                        The connecting element may be a surface rather than protrusions or indentations.";
                }
                identity EQUIPMENT_CATEGORY {
                    description "none";
                }
                identity EQUIPMENT_CATEGORY_SUBRACK {
                    base equipment-category;
                    description "An assembly with holders designed to accommodate CIRCUIT_PACKs. 
                        The assembly is designed to be mounted in a RACK.";
                }
                identity EQUIPMENT_CATEGORY_CIRCUIT_PACK {
                    base equipment-category;
                    description "An assembly with connectors compatible with those in a holder.
                        The assembly is designed to be mounted in a holder (SLOT) of a SUBRACK.
                        May also support holders (SLOTs) for SMALL_FORMFACTOR_PLUGGABLEs.";
                }
                identity EQUIPMENT_CATEGORY_SMALL_FORMFACTOR_PLUGGABLE {
                    base equipment-category;
                    description "A small assembly (compared to a CIRCUIT_PACK) with connectors compatible with those in a holder.
                        The assembly is designed to be mounted in a holder (SLOT) of a CIRCUIT_PACK or STAND_ALONE_UNIT.";
                }
                identity EQUIPMENT_CATEGORY_STAND_ALONE_UNIT {
                    base equipment-category;
                    description "An assembly with connectors for cabling and potentially with holders.
                        The assembly is designed to be mounted in a freeform environment (on a table or simple mechanical cabinet).
                        May support holders (SLOTs) for CIRCUIT_PACKs or for SMALL_FORMFACTOR_PLUGGABLEs.";
                }
                identity EQUIPMENT_CATEGORY_RACK {
                    base equipment-category;
                    description "A mechanical assembly with cabling and predefined mounting points for particular SUBRACK types.
                        The assembly is designed to be mounted on the floor in a row with other RACKs.";
                }
                identity HOLDER_CATEGORY {
                    description "none";
                }
                identity HOLDER_CATEGORY_SLOT {
                    base holder-category;
                    description "A guided holder with fixed connectors.
                        The guided holder is designed to take a particular form of CIRCUIT_PACK or SMALL_FORMFACTOR_PLUGGABLE";
                }
                identity FORWARDING_RULE {
                    description "none";
                }
                identity FORWARDING_RULE_CANNOT_FORWARD_ACROSS_FD_LINK {
                    base forwarding-rule;
                    description "LTPs referenced by the FD (or indirectly by the Link between FDs) cannot have FCs created between them.
                        This rule overrides all others.";
                }
                identity FORWARDING_RULE_MUST_FORWARD_ACROSS_FD_LINK {
                    base forwarding-rule;
                    description "LTPs referenced by the FD (or indirectly by the Link between FDs) MUST have FCs created between them.
                        This rule overrides all others except the CANNOT_FORWARD rule.";
                }
                identity FORWARDING_RULE_MAY_FORWARD_ACROSS_FD_LINK {
                    base forwarding-rule;
                    description "LTPs referenced by the FD (or indirectly by the Link between FDs) may have FCs created between them.
                        FCs may not be created between points that are not related by this rule either directly in an FD or indirectly via a Link linking two or more FDs.
                        For a Link points in an FD at one end of the Link can be connected to points in an FD at an other end of the Link.";
                }
                identity FORWARDING_RULE_NULL_FORWARDING_RULE {
                    base forwarding-rule;
                    description "none";
                }
                identity RULE_TYPE {
                    description "none";
                }
                identity RULE_TYPE_FORWARDING {
                    base rule-type;
                    description "The rule relates to creation of FCs.";
                }
                identity RULE_TYPE_COST {
                    base rule-type;
                    description "The rule relates to forwarding cost.";
                }
                identity RULE_TYPE_RISK {
                    base rule-type;
                    description "The rule relates to forwarding risk.";
                }
                identity RULE_TYPE_CAPACITY {
                    base rule-type;
                    description "none";
                }
                identity PORT_ROLE_RULE {
                    description "none";
                }
                identity PORT_ROLE_RULE_SAME_ROLE {
                    base port-role-rule;
                    description "none";
                }
                identity PORT_ROLE_RULE_DIFFERENT_ROLE {
                    base port-role-rule;
                    description "none";
                }
                identity PORT_ROLE_RULE_ANY_ROLE {
                    base port-role-rule;
                    description "none";
                }
                identity SIGNAL_PROPERTY_VALUE_RULE {
                    description "none";
                }
                identity SIGNAL_PROPERTY_VALUE_RULE_SAME_VALUE {
                    base signal-property-value-rule;
                    description "none";
                }
                identity SIGNAL_PROPERTY_VALUE_RULE_ANY_VALUE {
                    base signal-property-value-rule;
                    description "none";
                }
                identity TERMINATION_DIRECTION {
                    description "none";
                }
                identity TERMINATION_DIRECTION_BIDIRECTIONAL {
                    base termination-direction;
                    description "A Termination with both SINK and SOURCE flows.";
                }
                identity TERMINATION_DIRECTION_SINK {
                    base termination-direction;
                    description "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity.";
                }
                identity TERMINATION_DIRECTION_SOURCE {
                    base termination-direction;
                    description "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity.";
                }
                identity TERMINATION_DIRECTION_UNDEFINED_OR_UNKNOWN {
                    base termination-direction;
                    description "Not a normal state. The system is unable to determine the correct value.";
                }
                identity TERMINATION_DIRECTION {
                    description "none";
                }
                identity TERMINATION_DIRECTION_BIDIRECTIONAL {
                    base termination-direction;
                    description "A Termination with both SINK and SOURCE flows.";
                }
                identity TERMINATION_DIRECTION_SINK {
                    base termination-direction;
                    description "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base termination-direction;
                    description "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base termination-direction;
                    description "Not a normal state. The system is unable to determine the correct value.";
                }
                identity ACTION_VERBS {
                    description "none";
                }
                identity ACTION_VERBS_CREATE_POST_ADD {
                    base action-verbs;
                    description "none";
                }
                identity ACTION_VERBS_SET_UPDATE_PUT_MODIFY_WRITE_ADD {
                    base action-verbs;
                    description "none";
                }
                identity ACTION_VERBS_GET_READ {
                    base action-verbs;
                    description "none";
                }
                identity ACTION_VERBS_DELETE_REMOVE {
                    base action-verbs;
                    description "none";
                }
                identity DIRECTION {
                    description "none";
                }
                identity DIRECTION_IN {
                    base direction;
                    description "none";
                }
                identity DIRECTION_OUT {
                    base direction;
                    description "none";
                }
                identity DIRECTION_BIDIRECTIONAL {
                    base direction;
                    description "none";
                }
                typedef forwarding-rule {
                    type identityref {
                        base forwarding-rule;
                    }
                    description "Rule that restricts the creation/deletion of an FC between points grouped by FD or related by the Link between FDs.";
                }
                typedef rule-type {
                    type identityref {
                        base rule-type;
                    }
                    description "Indicates the focus of the rule.";
                }
                grouping port-role-rule {
                    leaf-list port-role {
                        type port-role;
                        description "none";
                    }
                    leaf-list port-role-rule {
                        type port-role-rule;
                        description "none";
                    }
                    description "none";
                }
                typedef port-role-rule {
                    type identityref {
                        base port-role-rule;
                    }
                    description "none";
                }
                grouping signal-property-rule {
                    leaf signal-property-name {
                        type string;
                        description "none";
                    }
                    leaf signal-property-value-rule {
                        type signal-property-value-rule;
                        description "none";
                    }
                    leaf-list applicable-signal-value {
                        type string;
                        description "none";
                    }
                    description "none";
                }
                typedef signal-property-value-rule {
                    type identityref {
                        base signal-property-value-rule;
                    }
                    description "none";
                }


        /***********************
        * package ltp-capability
        **********************/ 
            /***********************
            * package object-classes
            **********************/ 
                grouping lp-spec {
                    leaf-list adapter-spec {
                        type leafref {
                            path '/core-model:lp-spec/core-model:lp-spec/core-model:adapter-spec/core-model:';
                        }
                        description "none";
                    }
                    leaf-list termination-spec {
                        type leafref {
                            path '/core-model:lp-spec/core-model:lp-spec/core-model:termination-spec/core-model:';
                        }
                        description "none";
                    }
                    leaf-list adapter-property-spec {
                        type leafref {
                            path '/core-model:lp-spec/core-model:lp-spec/core-model:adapter-property-spec/core-model:';
                        }
                        description "none";
                    }
                    leaf provider-view-spec {
                        type leafref {
                            path '/core-model:lp-spec/core-model:lp-spec/core-model:provider-view-spec/core-model:';
                        }
                        description "none";
                    }
                    leaf-list server-spec {
                        type leafref {
                            path '/core-model:lp-spec/core-model:lp-spec/core-model:server-spec/core-model:';
                        }
                        description "none";
                    }
                    leaf-list connection-spec {
                        type leafref {
                            path '/core-model:lp-spec/core-model:lp-spec/core-model:connection-spec/core-model:';
                        }
                        description "none";
                    }
                    leaf-list lp-spec {
                        type leafref {
                            path '/core-model:lp-spec/core-model:lp-spec/core-model:';
                        }
                        description "none";
                    }
                    leaf spec-target-class {
                        type metaclass-class-name;
                        default "LayerProtocol";
                        description "
                            range of type : LayerProtocol";
                    }
                    description "The specification of the capabilities of a specific type of LP.";
                }
                grouping client-spec {
                    leaf-list mapping-interaction-rule {
                        type leafref {
                            path '/core-model:lp-spec/core-model:lp-spec/core-model:adapter-property-spec/core-model:owned-mapping-interaction-rule/core-model:';
                        }
                        description "none";
                    }
                    description "The specification of a client layer protocol supported by the adapter of an LP.";
                }
                grouping mapping-interaction-rule {
                    description "The specification of the interaction between the support for different client layer protocol signals.
                        For example an LP that supports 20 layer protocol X signals and 5 layer protocol Y signals may be such that a particular layer protocol X instance being used eliminates the possibility of using a particular layer protocol Y instance being used.";
                }
                grouping termination-spec {
                    leaf connection-spec {
                        type leafref {
                            path '/core-model:lp-spec/core-model:lp-spec/core-model:connection-spec/core-model:';
                        }
                        description "none";
                    }
                    leaf-list adapter-property-spec {
                        type leafref {
                            path '/core-model:lp-spec/core-model:lp-spec/core-model:adapter-property-spec/core-model:';
                        }
                        description "none";
                    }
                    description "The specification of the layer protocol termination (including framing, modulation etc.).
                        For example, the specification of the function that takes a MAC frame and extracts the content (removing the MAC address in the process).";
                }
                grouping adapter-property-spec {
                    leaf-list pool-property-spec {
                        type leafref {
                            path '/core-model:lp-spec/core-model:lp-spec/core-model:adapter-property-spec/core-model:pool-property-spec/core-model:';
                        }
                        description "none";
                    }
                    leaf-list constraining-mapping-interaction-rule {
                        type leafref {
                            path '/core-model:lp-spec/core-model:lp-spec/core-model:adapter-property-spec/core-model:owned-mapping-interaction-rule/core-model:';
                        }
                        description "none";
                    }
                    leaf-list owned-mapping-interaction-rule {
                        type leafref {
                            path '/core-model:lp-spec/core-model:lp-spec/core-model:adapter-property-spec/core-model:owned-mapping-interaction-rule/core-model:';
                        }
                        description "none";
                    }
                    description "The specification of the properties of the client side adapter of an LP.";
                }
                grouping pool-property-spec {
                    leaf client-spec {
                        type leafref {
                            path '/core-model:lp-spec/core-model:lp-spec/core-model:adapter-property-spec/core-model:pool-property-spec/core-model:client-spec/core-model:';
                        }
                        description "none";
                    }
                    leaf client-capacity {
                        type to-be-defined;
                        description "none";
                    }
                    leaf-list adapter-property-spec {
                        type leafref {
                            path '/core-model:lp-spec/core-model:lp-spec/core-model:adapter-property-spec/core-model:';
                        }
                        description "none";
                    }
                    description "The specification for the properties of the pool of available instances of a particular client layer protocol.
                        This may cover numbering range, capacity, number of instances etc.";
                }
                grouping connection-spec {
                    leaf-list connection-spec {
                        type leafref {
                            path '/core-model:lp-spec/core-model:lp-spec/core-model:connection-spec/core-model:';
                        }
                        description "Allows for specification of complex connectivity between multiple terminations in a sophisticated LP.";
                    }
                    description "The specification of the flexibility of the association between the ConnectionPoint and the Termination of the LP.";
                }
                grouping connection-point-and-adapter-spec {
                    leaf connection-spec {
                        type leafref {
                            path '/core-model:lp-spec/core-model:lp-spec/core-model:connection-spec/core-model:';
                        }
                        description "none";
                    }
                    leaf pool-property-spec {
                        type leafref {
                            path '/core-model:lp-spec/core-model:lp-spec/core-model:adapter-property-spec/core-model:pool-property-spec/core-model:';
                        }
                        description "The specification of the server facing connection point and the adapter that deals with the transformation of a single signal of the layer protocol to/from the server.
                            Equialent to an ITU-T CTP [ITU-T G.8052].";
                    }
                    description "The specification of the server facing connection point and the adapter that deals with the transformation of a single signal of the layer protocol to/from the server.
                        Equialent to an ITU-T CTP [ITU-T G.8052].";
                }
                grouping provider-view-spec {
                    leaf-list pool-property-spec {
                        type leafref {
                            path '/core-model:lp-spec/core-model:lp-spec/core-model:adapter-property-spec/core-model:pool-property-spec/core-model:';
                        }
                        description "none";
                    }
                    description "The specification of the properties of an LP at the base of a virtual/floating LTP that relate to the provider of capacity/capability for that floating LTP.";
                }
                grouping server-spec {
                    description "The specification of the server side of an LP at the base of an LTP that supports the creation of server LTPs for use in an inverse multiplexing scheme.";
                }
                grouping ltp-spec {
                    leaf-list lp-spec {
                        type leafref {
                            path '/core-model:lp-spec/core-model:lp-spec/core-model:';
                        }
                        min-elements 1;
                        description "none";
                    }
                    leaf spec-target-class {
                        type metaclass-class-name;
                        default "LogicalTerminationPoint";
                        description "
                            range of type : LogicalTerminationPoint";
                    }
                    description "The specification of a specific type of LTP.";
                }


        /***********************
        * package type-definitions
        **********************/ 
            identity PORT_DIRECTION {
                description "none";
            }
            identity PORT_DIRECTION_BIDIRECTIONAL {
                base port-direction;
                description "The Port has both an INPUT flow and an OUTPUT flow defined.";
            }
            identity PORT_DIRECTION_INPUT {
                base port-direction;
                description "The Port only has definition for a flow into the Forwarding entity (i.e. an ingress flow).";
            }
            identity PORT_DIRECTION_OUTPUT {
                base port-direction;
                description "The Port only has definition for a flow out of the Forwarding entity (i.e. an egress flow).";
            }
            identity PORT_DIRECTION_UNIDENTIFIED_OR_UNKNOWN {
                base port-direction;
                description "Not a normal state. The system is unable to determine the correct value.";
            }
            identity PORT_DIRECTION_OMNIDIRECTIONAL {
                base port-direction;
                description "none";
            }
            identity FORWARDING_DIRECTION {
                description "none";
            }
            identity FORWARDING_DIRECTION_BIDIRECTIONAL {
                base forwarding-direction;
                description "The Forwarding entity supports both BIDIRECTIONAL flows at all Ports (i.e. all Ports have both an INPUT flow and an OUTPUT flow defined).";
            }
            identity FORWARDING_DIRECTION_UNIDIRECTIONAL {
                base forwarding-direction;
                description "The Forwarding entity has Ports that are either INPUT or OUTPUT. It has no BIDIRECTIONAL Ports.";
            }
            identity FORWARDING_DIRECTION_UNDEFINED_OR_UNKNOWN {
                base forwarding-direction;
                description "Not a normal state. The system is unable to determine the correct value.";
            }
            identity FORWARDING_DIRECTION_OMNIDIRECTIONAL {
                base forwarding-direction;
                description "none";
            }
            identity TERMINATION_DIRECTION {
                description "none";
            }
            identity TERMINATION_DIRECTION_BIDIRECTIONAL {
                base termination-direction;
                description "A Termination with both SINK and SOURCE flows.";
            }
            identity TERMINATION_DIRECTION_SINK {
                base termination-direction;
                description "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base termination-direction;
                description "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base termination-direction;
                description "Not a normal state. The system is unable to determine the correct value.";
            }
            identity EXTENDED_TERMINATION_DIRECTION {
                description "none";
            }
            identity EXTENDED_TERMINATION_DIRECTION_CONTRA_DIRECTION_SINK {
                base extended-termination-direction;
                description "The essential flow of the Termination entity is SINK (i.e. up the layer stack) but the INPUT flow of the Termination entity was provided by a SOURCE OUTPUT or taken from a SOURCE INPUT (duplicating the input signal) hence reversing the flow orientation from down the layer stack to up the layer stack.";
            }
            identity EXTENDED_TERMINATION_DIRECTION_CONTRA_DIRECTION_SOURCE {
                base extended-termination-direction;
                description "The essential flow of the Termination entity is SOURCE (i.e. down the layer stack) but the OUTPUT flow of the Termination entity was fed to (and replaces) a SINK OUTPUT or was fed to a SINK INPUT (replacing the normal flow) hence reversing the flow orientation from down the layer stack to up the layer stack.";
            }
            identity TERMINATION_STATE {
                description "none";
            }
            identity TERMINATION_STATE_LP_CAN_NEVER_TERMINATE {
                base termination-state;
                description "A non-flexible case that can never be terminated.";
            }
            identity TERMINATION_STATE_LP_NOT_TERMINATED {
                base termination-state;
                description "A flexible termination that can terminate but is currently not terminated.";
            }
            identity TERMINATION_STATE_TERMINATED_SERVER_TO_CLIENT_FLOW {
                base termination-state;
                description "A flexible termination that is currently terminated for server to client flow only.";
            }
            identity TERMINATION_STATE_TERMINATED_CLIENT_TO_SERVER_FLOW {
                base termination-state;
                description "A flexible termination that is currently terminated for client to server flow only.";
            }
            identity TERMINATION_STATE_TERMINATED_BIDIRECTIONAL {
                base termination-state;
                description "A flexible termination that is currently terminated in both directions of flow.";
            }
            identity TERMINATION_STATE_LP_PERMENANTLY_TERMINATED {
                base termination-state;
                description "A non-flexible termination that is always terminated (in both directions of flow for a bidirectional case and in the one direction of flow for both unidirectional cases).";
            }
            identity TERMINATION_STATE_TERMINATION_STATE_UNKNOWN {
                base termination-state;
                description "There TerminationState cannot be determined.";
            }
            identity PROTECTION_REASON {
                description "none";
            }
            identity PROTECTION_REASON_WAIT_TO_REVERT {
                base protection-reason;
                description "The resource is selected as control is waiting to restore to a preferred resource.";
            }
            identity PROTECTION_REASON_SIGNAL_DEGRADE {
                base protection-reason;
                description "The resource is selected as the best preferred resource is in signal degrade.";
            }
            identity PROTECTION_REASON_SIGNAL_FAIL {
                base protection-reason;
                description "The resource is selected as the best preferred resource is in signal fail.";
            }
            identity ROUTE_SELECTION_CONTROL {
                description "none";
            }
            identity ROUTE_SELECTION_CONTROL_LOCK_OUT {
                base route-selection-control;
                description "The resource is configured to temporarily not be available for use in the protection scheme(s) it is part of.
                    This overrides all other protection control states including forced.
                    If the item is locked out, then it cannot be used under any circumstances.
                    Note: Only relevant when part of a protection scheme.
                    Note: if a protection process that has a relationship to the item (i.e. is one of the options the protection process may choose) is deactivated by being isFrozen = true) then the lockout request will be rejected. ";
            }
            identity ROUTE_SELECTION_REASON {
                description "none";
            }
            identity SWITCH_CONTROL {
                description "none";
            }
            identity SWITCH_CONTROL_NORMAL {
                base switch-control;
                description "No administrative control applied to the switch.";
            }
            identity SWITCH_CONTROL_MANUAL {
                base switch-control;
                description "Resource temporarily chosen by control configuration where the resource is not the preferred resource.
                    Preferred resource has highest priority.
                    Temporarily overrides reversion.
                    If this resource fails, it will switch to best available resource. 
                    If resource selected is shared and another FC requires the resource, then the selection control will change to Normal and switch to best available based upon normal rules.
                    Cannot manually switch a Forced switch, cannot remove a forced switch, cannot switch to a locked out item and will be rejected if the protection process is deactivated by being Freeze = true).
                    A manual switch/route that is selecting an FcPort, LTP, FC, Link or Route that is subsequently set to LOCK_OUT will have the manual removed (changed to NORMAL) and will switch away from the  FcPort with LOCK_OUT to best available based upon normal rules.
                    A manual switch that is selecting an FcPort that is subsequently selected by a Forced switch will be restored to normal operation and the manual will be removed.
                    A manual switch/route that is selecting an FcPort, LTP, FC, Link or Route that is subsequently manual selected by another switch/route  will have the manual removed and will switch away from the FcPort.
                    Can be returned to NORMAL by configuration action.";
            }
            identity SWITCH_CONTROL_FORCED {
                base switch-control;
                description "Resource temporarily chosen by control configuration where the resource is not the preferred resource.
                    Preferred resource has highest priority.
                    Temporarily overrides reversion.
                    If this resource fails it will NOT switch. 
                    If resource selected is shared and another FC requires the resource through a FORCE on that FC and the FC is of a higher FcPriority then the selection control on this FC will change to NORMAL and switch to best available based upon normal rules.
                    If the resource selected is then set to LOCK_OUT then the selection control will change to NORMAL and switch to best available based upon normal rules.
                    Can be returned to NORMAL by configuration action.";
            }
            identity SWITCH_STATE_REASON {
                description "none";
            }
            identity REVERSION_MODE {
                description "none";
            }
            identity REVERSION_MODE_REVERTIVE {
                base reversion-mode;
                description "An FC switched to a lower priority (non-preferred) resource will revert to a higher priority (preferred) resource when that recovers (potentially after some hold-off time).";
            }
            identity REVERSION_MODE_NON-REVERTIVE {
                base reversion-mode;
                description "An FC switched to a lower priority (non-preferred) resource will not revert to a higher priority (preferred) resource when that recovers.";
            }
            identity RESILIENCE_CONTROL {
                description "none";
            }
            identity RESILIENCE_CONTROL_QUIESCENT {
                base resilience-control;
                description "none";
            }
            identity RESILIENCE_CONTROL_RESTORING {
                base resilience-control;
                description "none";
            }
            identity RESILIENCE_CONTROL_RECOVERY_FAILED {
                base resilience-control;
                description "none";
            }
            identity RESILIENCE_CONTROL_UNKNOWN {
                base resilience-control;
                description "none";
            }
            identity RUN_MODE {
                description "none";
            }
            identity RUN_MODE_FREE_RUN {
                base run-mode;
                description "The ckock is not synchronized to another clock.";
            }
            identity RUN_MODE_LOCKED {
                base run-mode;
                description "The clock is synchronised to another clock.";
            }
            identity RUN_MODE_HOLD_OVER {
                base run-mode;
                description "The clock was previously synchonised to another clock but that timing input has been lost.
                    The clock is set to the last known synchronization.";
            }
            identity OPERATIONAL_STATE {
                description "none";
            }
            identity OPERATIONAL_STATE_DISABLED {
                base operational-state;
                description "The resource is unable to meet the SLA of the user of the resource. 
                    If no (explicit) SLA is defined the resource is disabled if it is totally inoperable and unable to provide service to the user.";
            }
            identity OPERATIONAL_STATE_ENABLED {
                base operational-state;
                description "The resource is partially or fully operable and available for use.";
            }
            identity ADMINISTRATIVE_STATE {
                description "none";
            }
            identity ADMINISTRATIVE_STATE_LOCKED {
                base administrative-state;
                description "Users are administratively prohibited from making use of the resource.";
            }
            identity ADMINISTRATIVE_STATE_UNLOCKED {
                base administrative-state;
                description "Users are allowed to use the resource.";
            }
            identity ADMINISTRATIVE_STATE_SHUTTING_DOWN {
                base administrative-state;
                description "The entity is administratively restricted to existing instances of use only. There may be specific actions to remove existing uses. No new instances of use can be enabled.
                    The resource automatically transitions to “locked” when the last user quits. 
                    The administrative state is not visible in the client context. 
                    The lifecycle state “pending removal” should be used to indicate to the client that the provider intends to remove the resource.";
            }
            identity ADMINISTRATIVE_CONTROL {
                description "none";
            }
            identity ADMINISTRATIVE_CONTROL_UNLOCK {
                base administrative-control;
                description "The intention is for the entity to become unlocked.
                    The entity may already be UNLOCKED.";
            }
            identity ADMINISTRATIVE_CONTROL_LOCK_PASSIVE {
                base administrative-control;
                description "The intention is for the entity to become locked but no effort is expected to move to the Locked state (the state will be achieved once all users stop using the resource). 
                    The entity may be LOCKED.";
            }
            identity ADMINISTRATIVE_CONTROL_LOCK_ACTIVE {
                base administrative-control;
                description "The intention is for the entity to become locked and it is expected that effort will be made to move to the Locked state (users will be actively removed). 
                    The entity may already be LOCKED.";
            }
            identity ADMINISTRATIVE_CONTROL_LOCK_IMMEDIATE {
                base administrative-control;
                description "The intention is for the entity to become locked and it is expected to move to the Locked state immediately (users will be force removed). 
                    The entity may already be LOCKED.";
            }
            identity ADMINISTRATIVE_CONTROL_QUIESCENT {
                base administrative-control;
                description "The administrative state is at a stable value (LOCKED/UNLOCKED) and no action is being taken.";
            }
            identity LIFECYCLE_STATE {
                description "none";
            }
            identity LIFECYCLE_STATE_PLANNED {
                base lifecycle-state;
                description "The resource is planned but is not present in the network.
                    Should include a 'time' when the resources are expected to be installed.";
            }
            identity LIFECYCLE_STATE_POTENTIAL_AVAILABLE {
                base lifecycle-state;
                description "The supporting resources are present in the network but are shared with other clients; or require further configuration before they can be used; or both.
                    (1) When a potential resource is configured and allocated to a client it is moved to the INSTALLED state for that client.
                    (2) If the potential resource has been consumed (e.g. allocated to another client) it is moved to the POTENTIAL BUSY state for all other clients.";
            }
            identity LIFECYCLE_STATE_POTENTIAL_BUSY {
                base lifecycle-state;
                description "The supporting resources are present in the network but have been allocated to other clients.";
            }
            identity LIFECYCLE_STATE_INSTALLED {
                base lifecycle-state;
                description "The resource is present in the network and is capable of providing the service.";
            }
            identity LIFECYCLE_STATE_PENDING_REMOVAL {
                base lifecycle-state;
                description "The resource has been marked for removal.  Should include a “time” when the resources are expected to be removed.";
            }
            identity BLOCK_DIRECTION {
                description "none";
            }
            identity BLOCK_DIRECTION_NO_BLOCK {
                base block-direction;
                description "none";
            }
            identity ACTION_VERBS {
                description "none";
            }
            identity ACTION_VERBS_CREATE_POST_ADD {
                base action-verbs;
                description "none";
            }
            identity ACTION_VERBS_SET_UPDATE_PUT_MODIFY_WRITE_ADD {
                base action-verbs;
                description "none";
            }
            identity ACTION_VERBS_GET_READ {
                base action-verbs;
                description "none";
            }
            identity ACTION_VERBS_DELETE_REMOVE {
                base action-verbs;
                description "none";
            }
            identity ACTIVITY_DIRECTIVE {
                description "none";
            }
            identity ACTIVITY_DIRECTIVE_STRUCTURE_IS_NOT {
                base activity-directive;
                description "none";
            }
            identity ACTIVITY_DIRECTIVE_NEW_STRUCTURE_AND_VALUES {
                base activity-directive;
                description "none";
            }
            identity ACTIVITY_DIRECTIVE_INCREMENTAL_STRUCTURE_AND_VALUES {
                base activity-directive;
                description "none";
            }
            identity ACTIVITY_DIRECTIVE_ONLY_VALUES_IN_EXISTING_STRUCTURE {
                base activity-directive;
                description "none";
            }
            identity ACTIVITY_DIRECTIVE_DEFINED_BY_VERB {
                base activity-directive;
                description "none";
            }
            identity ACTION_EFFORT {
                description "none";
            }
            identity ACTION_EFFORT_BEST_EFFORT {
                base action-effort;
                description "none";
            }
            identity ACTION_EFFORT_EXACT_MATCH {
                base action-effort;
                description "none";
            }
            identity PAUSE_RESUME_RULE {
                description "none";
            }
            identity PAUSE_RESUME_RULE_NO_PAUSE_POSSIBLE {
                base pause-resume-rule;
                description "none";
            }
            identity CONNECTOR_AND_PIN_ORIENTATION {
                description "none";
            }
            identity CONNECTOR_AND_PIN_ORIENTATION_MALE {
                base connector-and-pin-orientation;
                description "The connecting elements are dominantly protrusions.";
            }
            identity CONNECTOR_AND_PIN_ORIENTATION_FEMALE {
                base connector-and-pin-orientation;
                description "The connecting elements are dominantly indentations.";
            }
            identity CONNECTOR_AND_PIN_ORIENTATION_SYMMETRIC_NEUTRAL {
                base connector-and-pin-orientation;
                description "The pin (and housing) orientation combination is such that it is symmetric so a connector is compatible with itself.
                    The connecting element may be a surface rather than protrusions or indentations.";
            }
            identity EQUIPMENT_CATEGORY {
                description "none";
            }
            identity EQUIPMENT_CATEGORY_SUBRACK {
                base equipment-category;
                description "An assembly with holders designed to accommodate CIRCUIT_PACKs. 
                    The assembly is designed to be mounted in a RACK.";
            }
            identity EQUIPMENT_CATEGORY_CIRCUIT_PACK {
                base equipment-category;
                description "An assembly with connectors compatible with those in a holder.
                    The assembly is designed to be mounted in a holder (SLOT) of a SUBRACK.
                    May also support holders (SLOTs) for SMALL_FORMFACTOR_PLUGGABLEs.";
            }
            identity EQUIPMENT_CATEGORY_SMALL_FORMFACTOR_PLUGGABLE {
                base equipment-category;
                description "A small assembly (compared to a CIRCUIT_PACK) with connectors compatible with those in a holder.
                    The assembly is designed to be mounted in a holder (SLOT) of a CIRCUIT_PACK or STAND_ALONE_UNIT.";
            }
            identity EQUIPMENT_CATEGORY_STAND_ALONE_UNIT {
                base equipment-category;
                description "An assembly with connectors for cabling and potentially with holders.
                    The assembly is designed to be mounted in a freeform environment (on a table or simple mechanical cabinet).
                    May support holders (SLOTs) for CIRCUIT_PACKs or for SMALL_FORMFACTOR_PLUGGABLEs.";
            }
            identity EQUIPMENT_CATEGORY_RACK {
                base equipment-category;
                description "A mechanical assembly with cabling and predefined mounting points for particular SUBRACK types.
                    The assembly is designed to be mounted on the floor in a row with other RACKs.";
            }
            identity HOLDER_CATEGORY {
                description "none";
            }
            identity HOLDER_CATEGORY_SLOT {
                base holder-category;
                description "A guided holder with fixed connectors.
                    The guided holder is designed to take a particular form of CIRCUIT_PACK or SMALL_FORMFACTOR_PLUGGABLE";
            }
            identity FORWARDING_RULE {
                description "none";
            }
            identity FORWARDING_RULE_CANNOT_FORWARD_ACROSS_FD_LINK {
                base forwarding-rule;
                description "LTPs referenced by the FD (or indirectly by the Link between FDs) cannot have FCs created between them.
                    This rule overrides all others.";
            }
            identity FORWARDING_RULE_MUST_FORWARD_ACROSS_FD_LINK {
                base forwarding-rule;
                description "LTPs referenced by the FD (or indirectly by the Link between FDs) MUST have FCs created between them.
                    This rule overrides all others except the CANNOT_FORWARD rule.";
            }
            identity FORWARDING_RULE_MAY_FORWARD_ACROSS_FD_LINK {
                base forwarding-rule;
                description "LTPs referenced by the FD (or indirectly by the Link between FDs) may have FCs created between them.
                    FCs may not be created between points that are not related by this rule either directly in an FD or indirectly via a Link linking two or more FDs.
                    For a Link points in an FD at one end of the Link can be connected to points in an FD at an other end of the Link.";
            }
            identity FORWARDING_RULE_NULL_FORWARDING_RULE {
                base forwarding-rule;
                description "none";
            }
            identity RULE_TYPE {
                description "none";
            }
            identity RULE_TYPE_FORWARDING {
                base rule-type;
                description "The rule relates to creation of FCs.";
            }
            identity RULE_TYPE_COST {
                base rule-type;
                description "The rule relates to forwarding cost.";
            }
            identity RULE_TYPE_RISK {
                base rule-type;
                description "The rule relates to forwarding risk.";
            }
            identity RULE_TYPE_CAPACITY {
                base rule-type;
                description "none";
            }
            identity PORT_ROLE_RULE {
                description "none";
            }
            identity PORT_ROLE_RULE_SAME_ROLE {
                base port-role-rule;
                description "none";
            }
            identity PORT_ROLE_RULE_DIFFERENT_ROLE {
                base port-role-rule;
                description "none";
            }
            identity PORT_ROLE_RULE_ANY_ROLE {
                base port-role-rule;
                description "none";
            }
            identity SIGNAL_PROPERTY_VALUE_RULE {
                description "none";
            }
            identity SIGNAL_PROPERTY_VALUE_RULE_SAME_VALUE {
                base signal-property-value-rule;
                description "none";
            }
            identity SIGNAL_PROPERTY_VALUE_RULE_ANY_VALUE {
                base signal-property-value-rule;
                description "none";
            }
            identity TERMINATION_DIRECTION {
                description "none";
            }
            identity TERMINATION_DIRECTION_BIDIRECTIONAL {
                base termination-direction;
                description "A Termination with both SINK and SOURCE flows.";
            }
            identity TERMINATION_DIRECTION_SINK {
                base termination-direction;
                description "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity.";
            }
            identity TERMINATION_DIRECTION_SOURCE {
                base termination-direction;
                description "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity.";
            }
            identity TERMINATION_DIRECTION_UNDEFINED_OR_UNKNOWN {
                base termination-direction;
                description "Not a normal state. The system is unable to determine the correct value.";
            }
            identity TERMINATION_DIRECTION {
                description "none";
            }
            identity TERMINATION_DIRECTION_BIDIRECTIONAL {
                base termination-direction;
                description "A Termination with both SINK and SOURCE flows.";
            }
            identity TERMINATION_DIRECTION_SINK {
                base termination-direction;
                description "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base termination-direction;
                description "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base termination-direction;
                description "Not a normal state. The system is unable to determine the correct value.";
            }
            identity ACTION_VERBS {
                description "none";
            }
            identity ACTION_VERBS_CREATE_POST_ADD {
                base action-verbs;
                description "none";
            }
            identity ACTION_VERBS_SET_UPDATE_PUT_MODIFY_WRITE_ADD {
                base action-verbs;
                description "none";
            }
            identity ACTION_VERBS_GET_READ {
                base action-verbs;
                description "none";
            }
            identity ACTION_VERBS_DELETE_REMOVE {
                base action-verbs;
                description "none";
            }
            identity DIRECTION {
                description "none";
            }
            identity DIRECTION_IN {
                base direction;
                description "none";
            }
            identity DIRECTION_OUT {
                base direction;
                description "none";
            }
            identity DIRECTION_BIDIRECTIONAL {
                base direction;
                description "none";
            }
            grouping metaclass-class {
                leaf name {
                    type metaclass-class-name;
                    description "The text name of the Class";
                }
                description "This datatype represents the '<<Metaclass>> Class' from the UML metamodel. 
                    An instance of the referencing Class (e.g. LTP) will reference a Class (not an instance).
                    This referenced Class will provide definition to extend the referencing instance. 
                    So, for example, an LTP instance will have the attributes defined in the LTP class and also the attributes defined in the referenced Class (an LtpSpec).
                    The referenced Class may:
                    (1) provide invariant properties (that are the same for many instances) that then are not conveyed with the referencing instance.
                    (2) provide definitions for attributes that are present in the instance that are not defined in the Class of the instance (these attribute may have been pruned and refactored from one or more external definition sources). 
                    (3) apply constraints to attributes in the instance that were defined in the class of the referencing instance.
                    (4) replace attributes that were present in the class of the referencing instance by a new definition (same name).
                    ";
            }
            typedef metaclass-class-name {
                type string;
                description "none";
            }

        /***********************
        * package spec-pattern
        **********************/ 
            /***********************
            * package object-classes
            **********************/ 
                grouping composed-part {
                    list part-spec-reference-class-ref {
                        if-feature spectargetclass-entity/composedpart;
                        min-elements 1;
                        uses metaclass-class;
                        description "none";
                    }
                    description "none";
                }
                grouping entity {
                    leaf-list extension-container {
                        type leafref {
                            path '/core-model:entity/core-model:extension-container/core-model:';
                        }
                        description "none";
                    }
                    leaf-list composed-part {
                        type leafref {
                            path '/core-model:entity/core-model:composed-part/core-model:';
                        }
                        description "none";
                    }
                    list entity-spec-reference-class-ref {
                        if-feature spectargetclass-entity;
                        min-elements 1;
                        uses metaclass-class;
                        description "none";
                    }
                    description "none";
                }
                grouping entity-spec {
                    leaf-list part-spec {
                        type leafref {
                            path '/core-model:entity-spec/core-model:part-spec/core-model:';
                        }
                        description "none";
                    }
                    leaf spec-target-class {
                        type metaclass-class-name;
                        description "
                            range of type : Entity, Entity/ExtensionContainer";
                    }
                    description "none";
                }
                grouping extension-container {
                    list entity-spec-reference-class-ref {
                        if-feature spectargetclass-entity/extensioncontainer;
                        min-elements 1;
                        uses metaclass-class;
                        description "none";
                    }
                    description "none";
                }
                grouping part-spec {
                    leaf spec-target-class {
                        type metaclass-class-name;
                        description "
                            range of type : Entity/ComposedPart";
                    }
                    description "none";
                }
                feature spectargetclass-entity/composedpart {
                    description "none";
                }
                feature spectargetclass-entity {
                    description "none";
                }
                feature spectargetclass-entity/extensioncontainer {
                    description "none";
                }



    /***********************
    * package general-controller-model
    **********************/ 
        /***********************
        * package associations
        **********************/ 

        /***********************
        * package object-classes
        **********************/ 
            /***********************
            * package explanatory-classes
            **********************/ 
                grouping compute-function {
                    description "A generalized computational function with no particular specialization.
                        The specialization will be stated via a spec.";
                }
                grouping controlled-entity {
                    description "The entity that is controlled by the controller at the focus of the view.
                        The entity may be an LTP, an FC etc.
                        Note that the controlled entity may be another controller.";
                }
                grouping control-policies {
                    description "Policy governing the controller";
                }
                grouping control-function-abstraction {
                    uses processing-construct;
                    description "The view of a functional component that forms part of the system that supports the ControlComponent.
                        ControlComponents are presented by the ControlComponent itself to another ControlComponent for the purpose of control of control.
                        ";
                }
                grouping controller-internal-view {
                    leaf-list subordinate-exposed-view {
                        type leafref {
                            path '/core-model:subordinate-exposed-view/core-model:';
                        }
                        description "none";
                    }
                    uses control-system-view;
                    description "The view the controller has of the controller environment.";
                }
                grouping exposed-view-of-control-entities {
                    leaf-list control-function-abstraction {
                        type leafref {
                            path '/core-model:control-function-abstraction/core-model:';
                        }
                        description "none";
                    }
                    leaf-list control-port {
                        type leafref {
                            path '/core-model:control-component/core-model:control-port/core-model:';
                        }
                        min-elements 1;
                        description "none";
                    }
                    uses control-system-view;
                    uses constraint-domain;
                    description "The presented view of the controller for the purpose of controlling the controller.";
                }
                grouping exposed-view-of-controlled-entities {
                    leaf-list control-port {
                        type leafref {
                            path '/core-model:control-component/core-model:control-port/core-model:';
                        }
                        min-elements 1;
                        description "none";
                    }
                    leaf-list abstract-view {
                        type leafref {
                            path '/core-model:abstract-view/core-model:';
                        }
                        description "none";
                    }
                    leaf-list subordinate-exposed-view {
                        type leafref {
                            path '/core-model:subordinate-exposed-view/core-model:';
                        }
                        description "none";
                    }
                    uses control-system-view;
                    description "The view exposed of the controlled environment for the purpose of controlling the controlled environment via the controller.";
                }
                grouping abstract-view {
                    uses control-system-view;
                    description "none";
                }
                grouping exposed-view {
                    leaf exposed-view-of-control-entities {
                        type leafref {
                            path '/core-model:exposed-view-of-control-entities/core-model:';
                        }
                        description "none";
                    }
                    leaf exposed-view-of-controlled-entities {
                        type leafref {
                            path '/core-model:exposed-view-of-controlled-entities/core-model:';
                        }
                        description "none";
                    }
                    leaf-list port-to-controller {
                        type leafref {
                            path '/core-model:control-component/core-model:control-port/core-model:';
                        }
                        min-elements 1;
                        description "none";
                    }
                    uses control-system-view;
                    uses constraint-domain;
                    description "none";
                }
                grouping subordinate-exposed-view {
                    leaf control-exposed-view {
                        type leafref {
                            path '/core-model:exposed-view/core-model:';
                        }
                        description "none";
                    }
                    uses exposed-view;
                    uses control-system-view;
                    description "Is a pruned and refactored view of a view provided by a ControlComponent subordinate to the ControlComponent providing the ControlView.";
                }
                grouping function-network-element-control {
                    description "Traditional model of the NE equivalent to an aspect of the NetworkElement class from v1.2.
                        This class should not be implemented.";
                }
                grouping function-sdn-controller {
                    description "Traditional model of the SDN controller equivalent to the SdnController class from v1.2.
                        This class should not be implemented.";
                }
                grouping view-network-element-viewed-from-sdn-controller {
                    description "Traditional model of the view of the NE controller as seen from a SDN Controller equivalent to an aspect of the NetworkElement class from v1.2.
                        This class should not be implemented.";
                }
                grouping view-sdn-controller-viewed-from-manager {
                    description "Traditional model of the view of the SDN controller as seen from a manager .
                        No equivalent in v1.2.
                        This class should not be implemented.";
                }

            grouping control-component {
                leaf-list control-system-view {
                    type leafref {
                        path '/core-model:control-system-view/core-model:';
                    }
                    description "none";
                }
                leaf-list defining-view-mapping {
                    type leafref {
                        path '/core-model:view-mapping/core-model:';
                    }
                    min-elements 1;
                    description "ControlComponent behavior is defined in part by view mappings.";
                }
                leaf-list control-port {
                    type leafref {
                        path '/core-model:control-component/core-model:control-port/core-model:';
                    }
                    description "none";
                }
                leaf-list subordinate-control-component-view {
                    type leafref {
                        path '/core-model:control-component/core-model:';
                    }
                    description "A ControlComponent that is part of an abstract view of the system that supports the referencing ControlComponent and hence describes part of the behavior of the referencing ControlComponent.";
                }
                leaf-list view-mapping {
                    type leafref {
                        path '/core-model:view-mapping/core-model:';
                    }
                    description "ControlComponent uses the referenced ViewMapping to produce one view from another.";
                }
                description "Represents control capability/functionality. The functionality is emergent from the running software.
                    ControlComponents communicate with other ControlComponents through ControlPorts about things expressed in the corresponding ControlSystemViews.
                    Examples of higher level aggregate ControlComponents are:
                    - the controller in the Network/Managed Element e.g. an SNMP agent).
                    - an SDN Controller.
                    - an EMS.
                    - an NMS.
                    Examples of lower level ControlComponents are:
                    - Path Computation.
                    - Problem Analytics.
                    This specific model follows a subset of the Component-System Pattern as that is all that is necessary for this aspect of expression. 
                    ";
            }
            grouping control-port {
                leaf-list protecting-control-port {
                    type leafref {
                        path '/core-model:control-component/core-model:control-port/core-model:';
                    }
                    description "A simple representation of resilience where one ControlPorts are identified as providing equivalent information.";
                }
                leaf control-port {
                    type leafref {
                        path '/core-model:control-component/core-model:control-port/core-model:';
                    }
                    description "Control Ports may be used to associate controllers in a hierarch and as peers.
                        Peer controllers are assumed to both the subordinate of each other.";
                }
                leaf ltp {
                    type leafref {
                        path '/core-model:network-control-domain/core-model:network-element/core-model:ltp/core-model:';
                    }
                    description "The LTP through which the control messaging/signaling flows.";
                }
                description "The access to the ControlComponent following the normal Component-Port pattern (i.e. the functions of a component are accessed via ports).
                    Is assumed to usually be bidirectional.";
            }
            grouping control-system-view {
                leaf-list ltp {
                    type leafref {
                        path '/core-model:network-control-domain/core-model:network-element/core-model:ltp/core-model:';
                    }
                    description "LTP in ControlSystemView";
                }
                leaf-list fd {
                    type leafref {
                        path '/core-model:network-control-domain/core-model:network-element/core-model:fd/core-model:';
                    }
                    description "FD in ControlSystemView";
                }
                leaf-list link {
                    type leafref {
                        path '/core-model:link/core-model:';
                    }
                    description "Link in ControlSystemView";
                }
                leaf-list fc {
                    type leafref {
                        path '/core-model:network-control-domain/core-model:network-element/core-model:ltp/core-model:embedded-clock/core-model:encapsulated-fc/core-model:';
                    }
                    description "FC in ControlSystemView";
                }
                leaf-list pc {
                    type leafref {
                        path '/core-model:equipment/core-model:encapsulated-non-fru/core-model:foundation-pc/core-model:';
                    }
                    description "PC in ControlSystemView";
                }
                leaf-list cd {
                    type leafref {
                        path '/core-model:constraint-domain/core-model:';
                    }
                    description "CD in ControlSystemView";
                }
                leaf-list equipment {
                    type leafref {
                        path '/core-model:equipment/core-model:encapsulated-non-fru/core-model:';
                    }
                    description "Equipment in ControlSystemView";
                }
                leaf-list subordinate-control-system-view {
                    type leafref {
                        path '/core-model:control-system-view/core-model:';
                    }
                    description "A ControlSystemView that is a subset of this ControlSystemView providing more detail.";
                }
                leaf-list control-port {
                    type leafref {
                        path '/core-model:control-component/core-model:control-port/core-model:';
                    }
                    description "Port of ControlComponent through which the referencing ControlSystemView is accessed.";
                }
                leaf-list control-component {
                    type leafref {
                        path '/core-model:control-component/core-model:';
                    }
                    description "A ControlComponent (subordinate) that is in this ControlSystemView (superior) which was provided by another ControlComponent (superior). 
                        The ControlComponent (subordinate) will have exposed its own ControlSystemViews (original subordinate).
                        These ControlSystemViews (original subordinate) will be pruned and refactored by the ControlComponent (superior) to be presented in the ControlSystemView (superior) under the view of the ControlComponent (subordinate) as a ControlSystemView (pruned and refactored subordinate).
                        The ControlSystemView (pruned and refactored subordinate) will have other components represented that may include ControlComponents. The process is recursive.
                        ";
                }
                description "A view of the things controlled by a control system.
                    A ControlSystemView is structured presentation of the underlying controlled things (the 'actual' entities) for some purpose.
                    The ControlSystemView is constructed by pruning and refactoring the models of the underlying controlled things.
                    Is an aggregation of 'views of things' where a 'view of things' is represented in abstraction by an Object Class in the model.
                    The ControlComponent is itself controlled and presents itself in terms of ControlComponents (subordinate) in a view.
                    At one extreme a ControlSystemView may expose all underlying details of everything controlled with no adjustment from the presentation provided by the controlled things.
                    A ControlSystemView may expose a subset of the controlled things that focuses on a particular aspect (e.g. only the ControlComponents).";
            }
            grouping view-mapping {
                leaf-list controller-internal-view {
                    type leafref {
                        path '/core-model:controller-internal-view/core-model:';
                    }
                    min-elements 1;
                    max-elements 2;
                    description "none";
                }
                leaf-list control-system-view {
                    type leafref {
                        path '/core-model:control-system-view/core-model:';
                    }
                    min-elements 2;
                    max-elements 2;
                    description "none";
                }
                description "The rules that relate one view to another.";
            }


    /***********************
    * package processing-construct-model
    **********************/ 
        /***********************
        * package object-classes
        **********************/ 
            grouping processing-construct {
                leaf-list equipment {
                    type leafref {
                        path '/core-model:equipment/core-model:encapsulated-non-fru/core-model:';
                    }
                    description "The Equipment(s) that support the functionality of the PC.
                        This attribute is meaningful at the lowest level of PC recursion where the PC is supported by a single piece of Equipment.
                        At higher levels, the supporting equipment may be more difficult to evaluate especially where there is resilience and/or virtualization of some form.
                        This attribute allows diagnostics and engineering works impact evaluation.
                        In an implementation, the information may be acquired via a query on the equipment that exposes this reverse association. ";
                }
                leaf-list pc-port {
                    type leafref {
                        path '/core-model:equipment/core-model:encapsulated-non-fru/core-model:foundation-pc/core-model:pc-port/core-model:';
                    }
                    description "An asymmetric PC instance is related to LTPs via PcPorts (essentially the ports of the PC). 
                        Symmetric PCs don't have PcPorts and are directly related to LTPs.";
                }
                leaf-list ltp {
                    type leafref {
                        path '/core-model:network-control-domain/core-model:network-element/core-model:ltp/core-model:';
                    }
                    description "A symmetric PC instance is associated with zero or more LTP objects.  
                        The LTPs on the PC boundary provide information for processing and capacity for communication. 
                        For asymmetric PCs the association to the LTP is via the PcPort (with stated role, allowing access to a specific function of the PC).";
                }
                leaf-list cd {
                    type leafref {
                        path '/core-model:constraint-domain/core-model:';
                    }
                    description "One or more ConstraintDomains can constrain a ProcessingConstruct. 
                        A constrained PC connects LTPs on the boundary of the CD.";
                }
                leaf-list fd {
                    type leafref {
                        path '/core-model:network-control-domain/core-model:network-element/core-model:fd/core-model:';
                    }
                    description "One or more ForwardingDomains can constrain a ProcessingConstruct. 
                        A constrained PC connects LTPs on the boundary of the FD.";
                }
                leaf-list composed-pc {
                    type leafref {
                        path '/core-model:equipment/core-model:encapsulated-non-fru/core-model:foundation-pc/core-model:';
                    }
                    description "The PC class supports a recursive aggregation relationship (PcIsAssemblyOfPc).
                        This allows both:
                        - abstraction where an assembly of PCs (forming a System) is viewed as an abstract PC
                        - decomposition such that the internal construction of a PC can be exposed as multiple lower level PCs. 
                        Appropriate use of this association allows each of a collection of PCs to be decomposed into atomic parts (PCs) that can then be assembled into set of complex functions where each function in the set can be viewed as a PC.
                        Note that the model actually represents an aggregation of lower level PCs into higher level PCs as viewpoints rather than partitions, and supports multiple views.";
                }
                leaf pc-resilience-selector {
                    type leafref {
                        path '/core-model:equipment/core-model:encapsulated-non-fru/core-model:foundation-pc/core-model:pc-resilience-selector/core-model:';
                    }
                    description "PcResilienceSelector that realizes the resilience of the PC.";
                }
                uses global-class;
                description "ProcessingConstruct (PC) can be used to represent both potential and enabled processing between two or more of its PcPorts.
                    A PcPort may be associated with another PcPort or with an LTPs at a particular specific layerProtocol. 
                    Like the LTP, the PC supports any transport protocol including all circuit and packet forms. 
                    The PC is used to effect processing of information extracted from the transport layer protocol signal. 
                    A PC may be:
                    - Asymmetric such that it offers several function sans such that different functions are offered to different attached entities. 
                    - Symmetric such that it offers (or is considered as offering) only on function and the same function is offered to any attached entity with no interactions between functions offered to each attached entity
                    An asymmetric PC offerning a number of distinct functions will have PcPorts through which the distinct functions are accessed.
                    A symmetric PC offering only a single function need not have PcPorts, the function can be accessed directly from the PC. ";
            }
            grouping cd-port {
                leaf cd-port {
                    type leafref {
                        path '/core-model:constraint-domain/core-model:cd-port/core-model:';
                    }
                    description "Constraint Domains can be meshed together view their ports directly as well as via LTPs indirectly.
                        ";
                }
                leaf-list ltp {
                    type leafref {
                        path '/core-model:network-control-domain/core-model:network-element/core-model:ltp/core-model:';
                    }
                    max-elements 2;
                    description "A CdPort is associated with zero or more LTP objects.  
                        The LTPs on the CD boundary provide capacity for processing. 
                        For symmetric CDs the association is directly from the CD to the LTP.";
                }
                leaf-list pc-port {
                    type leafref {
                        path '/core-model:equipment/core-model:encapsulated-non-fru/core-model:foundation-pc/core-model:pc-port/core-model:';
                    }
                    description "Where a CD is asymmetric and hence has CdPorts and where that CD  supports PCs, appropriate CdPorts of that CD support the corresponding PcPorts.";
                }
                uses local-class;
                description "The association of the CD to LTPs is direct for symmetric CDs and via CdPort for asymmetric CDs. 
                    The CdPort class models role based access to a CD.  
                    The capability to set up PCs between the associated CdPorts of a CD depends upon the type of CD. 
                    It is asymmetry in this capability that brings the need for CdPort.   
                    The CD can be considered as a component and the CdPort as a Port on that component.";
            }
            grouping constraint-domain {
                leaf-list cd-port {
                    type leafref {
                        path '/core-model:constraint-domain/core-model:cd-port/core-model:';
                    }
                    description "An asymmetric CD instance is related to LTPs via CdPorts (essentially the ports of the CD). 
                        Symmetric CDs don't have CdPorts and are directly related to LTPs.";
                }
                leaf-list pc {
                    type leafref {
                        path '/core-model:equipment/core-model:encapsulated-non-fru/core-model:foundation-pc/core-model:';
                    }
                    description "A CD constrains one or more PCs. 
                        A constrained PC connects LTPs that are on the CD boundary.";
                }
                leaf ltp {
                    type leafref {
                        path '/core-model:network-control-domain/core-model:network-element/core-model:ltp/core-model:';
                    }
                    description "A symmetric CD instance is associated with zero or more LTP objects.  
                        The LTPs on  the CD boundary provide capacity for processing. 
                        For asymmetric FDs the association to the LTP is via the FdPort.";
                }
                leaf-list composed-cd {
                    type leafref {
                        path '/core-model:constraint-domain/core-model:';
                    }
                    description "The CD class supports a recursive aggregation relationship (CdEncompassesCd) such that the internal construction of an CD can be exposed as multiple lower level CDs. 
                        Note that the model actually represents an aggregation of lower level CDs into higher level CDs as viewpoints rather than partitions, and supports multiple views";
                }
                leaf-list casc {
                    type leafref {
                        path '/core-model:network-control-domain/core-model:network-element/core-model:ltp/core-model:embedded-clock/core-model:encapsulated-fc/core-model:configuration-and-switch-control/core-model:';
                    }
                    description "A controller operating in the scope defined.";
                }
                leaf-list equipment {
                    type leafref {
                        path '/core-model:equipment/core-model:encapsulated-non-fru/core-model:';
                    }
                    description "A ConstraintDomain can be used to represent physical constraints in the logical view. 
                        In this case the CD can be associated to the physical equipment.";
                }
                leaf-list fc {
                    type leafref {
                        path '/core-model:network-control-domain/core-model:network-element/core-model:ltp/core-model:embedded-clock/core-model:encapsulated-fc/core-model:';
                    }
                    description "A CD constrains one or more FCs. 
                        A constrained FC connects LTPs that are on the CD boundary.";
                }
                leaf-list fd {
                    type leafref {
                        path '/core-model:network-control-domain/core-model:network-element/core-model:fd/core-model:';
                    }
                    description "A CD constrains one or more FDs. 
                        A constrained FD connects LTPs that are on the CD boundary.";
                }
                uses global-class;
                description "ConstraintDomain (CD) models the topological component that represents the opportunity to enable processing of information between two or more of its CdPorts.
                    A CdPort may be associated with another CdPort or with an LTPs at a particular specific layerProtocol. 
                    It provides the context for and constrains the formation, adjustment and removal of PCs and hence offers the potential to enable processing.  
                    The LTPs available are those defined at the boundary of the CD. 
                    CD can also be considered as the container of a view.
                    A CD may be:
                    - Asymmetric such that it offers several function sans such that different functions are offered to different attached entities. 
                    - Symmetric such that it offers (or is considered as offering) only on function and the same function is offered to any attached entity with no interactions between functions offered to each attached entity
                    An asymmetric CD offerning a number of distinct functions will have CdPorts through which the distinct functions are accessed.
                    A symmetric CD offering only a single function need not have CdPorts, the function can be accessed directly from the CD.";
            }
            grouping pc-port {
                leaf-list ltp {
                    type leafref {
                        path '/core-model:network-control-domain/core-model:network-element/core-model:ltp/core-model:';
                    }
                    max-elements 2;
                    description "A PC instance is associated with zero or more LTP objects.  
                        The LTPs on the PC boundary provide capacity for processing. 
                        For asymmetric PCs the association to the LTP is via the PcPort.";
                }
                leaf-list pc-port {
                    type leafref {
                        path '/core-model:equipment/core-model:encapsulated-non-fru/core-model:foundation-pc/core-model:pc-port/core-model:';
                    }
                    max-elements 2;
                    description "A PcPort can be directly bound to another PcPort (rather than via a LTP) to support a simplified application level view (rather than requiring the full transport level view).";
                }
                leaf-list fc-port {
                    type leafref {
                        path '/core-model:network-control-domain/core-model:network-element/core-model:ltp/core-model:embedded-clock/core-model:encapsulated-fc/core-model:fc-port/core-model:';
                    }
                    max-elements 2;
                    description "A PcPort can be directly bound to an FcPort (rather than via a LTP) to support a simplified application level view (rather than requiring the full transport level view). 
                        This is used to represent complex semantic associations between PCs where _pcPort direct association is not sufficient.";
                }
                leaf port-role {
                    type string;
                    description "Identifies the role of the port in the context of the specification of the PC.";
                }
                uses local-class;
                description "Represents the access to the functionality of a PC.";
            }
            grouping pc-resilience-selector {
                leaf-list pc {
                    type leafref {
                        path '/core-model:equipment/core-model:encapsulated-non-fru/core-model:foundation-pc/core-model:';
                    }
                    min-elements 2;
                    description "Alternative PC.";
                }
                uses local-class;
                description "Rudimentary resilience model for PC.";
            }

        /***********************
        * package associations
        **********************/ 


    /***********************
    * package example-fragments
    **********************/ 
        /***********************
        * package core-management-control-component-model
        **********************/ 

        /***********************
        * package core-operations-examples
        **********************/ 
            /***********************
            * package examples
            **********************/ 
                /***********************
                * package ltp
                **********************/ 
                    /***********************
                    * package pruned-model
                    **********************/ 
                        grouping logical-termination-point {
                            leaf-list physical-port-reference {
                                type string;
                                description "One or more text labels for the unmodeled physical port associated with the LTP.
                                    In many cases there is no associated physical port";
                            }
                            leaf ltp-direction {
                                type termination-direction;
                                description "The overall directionality of the LTP. 
                                    - A BIDIRECTIONAL LTP must have at least some LPs that are BIDIRECTIONAL but may also have some SINK and/or SOURCE LPs.
                                    - A SINK LTP can only contain SINK LPs
                                    - A SOURCE LTP can only contain SOURCE LPs";
                            }
                            leaf uuid {
                                type universal-id;
                                config false;
                                description "UUID: An identifier that is universally unique.
                                    (This should be considered in the context of Identifier: A property of an entity/role with a value that is unique within an identifier space, where the identifier space is itself globally unique, and immutable. An identifier carries no semantics with respect to the purpose or state of the entity)";
                            }
                            list address {
                                uses address;
                                description "One or more descriptions of the location.";
                            }
                            description "none";
                        }
                        grouping name-and-value {
                            leaf value-name {
                                type string;
                                description "The name of the value. The value need not have a name.";
                            }
                            leaf value {
                                type string;
                                description "The value.";
                            }
                            description "A scoped name-value pair";
                        }
                        typedef UniversalId {
                            type string;
                            description "The univeral ID value where the mechanism for generation is defned by some authority not directly referenced in the structure.";
                        }
                        typedef TerminationDirection {
                            type identityref {
                                base termination-direction;
                            }
                            description "The directionality of a termination entity.";
                        }
                        grouping address-element {
                            leaf address-element-name {
                                type string;
                                description "none";
                            }
                            container local-id {
                                uses local-id-and-class;
                                description "If the element is a localId (where the element above in the hierarchy must be the context in which the specific localId is relevant).";
                            }
                            leaf uuid {
                                type universal-id;
                                description "If the element is a uuid (where this element could be the top of a hierarchy but may also be at some level in the hierarchy where address navigation is considered necessary to assist in location of the UUID).";
                            }
                            container name {
                                uses name-and-class;
                                description "If the element is a name.";
                            }
                            container address {
                                uses address;
                                description "none";
                            }
                            leaf arbitrary-element {
                                type string;
                                description "Where the element is from some external model that is not formally represented in this model.";
                            }
                            description "One element of a hierarchy of elements.
                                Note that the element must have one and only one value chosen from a list of potential value types.";
                        }
                        grouping address {
                            leaf address-name {
                                type string;
                                description "The name of the address (to allow the specific hierarchy to be distinguished from others for the same entity).";
                            }
                            list address-element {
                                uses address-element;
                                description "none";
                            }
                            description "A description of location via a hierarchy of narrowing contexts.";
                        }
                        grouping local-id-and-class {
                            leaf class-of-instance {
                                type string;
                                description "The class to which the name refers.";
                            }
                            container local-id {
                                uses name-and-value;
                                description "The localId of the entity.";
                            }
                            description "The localId and the class of entity that it identifies.";
                        }
                        grouping name-and-class {
                            leaf class-of-instance {
                                type string;
                                description "The class to which the name refers.";
                            }
                            container name {
                                uses name-and-value;
                                description "If the element is a name.";
                            }
                            description "The name and the class of entity that it names.";
                        }

                    /***********************
                    * package instance-view-using-class-clones
                    **********************/ 
                        grouping logical-termination-point-instance-constraints {
                            leaf-list physical-port-reference {
                                type string;
                                config false;
                                description "One or more text labels for the unmodeled physical port associated with the LTP.
                                    In many cases there is no associated physical port";
                            }
                            leaf ltp-direction {
                                type termination-direction;
                                description "The overall directionality of the LTP. 
                                    - A BIDIRECTIONAL LTP must have at least some LPs that are BIDIRECTIONAL but may also have some SINK and/or SOURCE LPs.
                                    - A SINK LTP can only contain SINK LPs
                                    - A SOURCE LTP can only contain SOURCE LPs";
                            }
                            container address {
                                uses address;
                                description "One or more descriptions of the location.";
                            }
                            leaf uuid {
                                type universal-id;
                                config false;
                                description "UUID: An identifier that is universally unique.
                                    (This should be considered in the context of Identifier: A property of an entity/role with a value that is unique within an identifier space, where the identifier space is itself globally unique, and immutable. An identifier carries no semantics with respect to the purpose or state of the entity)";
                            }
                            uses global-class;
                            description "none";
                        }
                        grouping name-and-value {
                            leaf value-name {
                                type string;
                                description "The name of the value. The value need not have a name.";
                            }
                            leaf value {
                                type string;
                                description "The value.";
                            }
                            description "A scoped name-value pair.";
                        }
                        typedef UniversalId {
                            type string;
                            description "The univeral ID value where the mechanism for generation is defned by some authority not directly referenced in the structure.";
                        }
                        typedef TerminationDirection {
                            type identityref {
                                base termination-direction;
                            }
                            description "The directionality of a termination entity";
                        }
                        grouping global-class {
                            leaf-list local-id {
                                type string;
                                description "An identifier that is unique in the context of some scope that is less than the global scope.
                                    (This should be considered in the context of Identifier: A property of an entity/role with a value that is unique within an identifier space, where the identifier space is itself unique, and immutable. The identifier therefore represents the identity of the entity/role. An identifier carries no semantics with respect to the purpose of the entity.)";
                            }
                            leaf uuid {
                                type string;
                                config false;
                                description "UUID: An identifier that is universally unique.
                                    (This should be considered in the of Identifier: A property of an entity/role with a value that is unique within an identifier space, where the identifier space is itself globally unique, and immutable. An identifier carries no semantics with respect to the purpose or state of the entity)";
                            }
                            description "Represents a type of thing (an Entity) that has instances which can exist in their own right (independently of any others).
                                Entity: Has identity, defined boundary, properties, functionality and lifecycle in a global context.
                                (This should be considered in the context of a Class: (usage) The representation of a thing that may be an entity or an inseparable Entity Feature).";
                        }
                        typedef String {
                            type string;
                            description "String is a sequence of characters in some suitable character set used to display information about the model. Character sets may include non-Roman alphabets and characters.";
                        }
                        grouping address {
                            leaf address-name {
                                type string;
                                default "NeAddress";
                                description "The name of the address (to allow the specific hierarchy to be distinguished from others for the same entity).";
                            }
                            list address-element {
                                min-elements 2;
                                max-elements 2;
                                uses address-element-1;
                                description "none";
                            }
                            description "A description of location via a hierarchy of narrowing contexts.";
                        }
                        grouping address-element-1 {
                            leaf address-element-name {
                                type string;
                                description "none";
                            }
                            container local-id {
                                uses local-id-and-class;
                                description "If the element is a localId (where the element above in the hierarchy must be the context in which the specific localId is relevant).";
                            }
                            leaf uuid {
                                type universal-id;
                                description "If the element is a uuid (where this element could be the top of a hierarchy but may also be at some level in the hierarchy where address navigation is considered necessary to assist in location of the UUID).";
                            }
                            container name {
                                uses name-and-class;
                                description "If the element is a name.";
                            }
                            leaf arbitrary-element {
                                type string;
                                description "Where the element is from some external model that is not formally represented in this model.";
                            }
                            description "One element of a hierarchy of elements.
                                Note that the element must have one and only one value chosen from a list of potential value types.";
                        }
                        grouping address-element-2 {
                            leaf address-element-name {
                                type string;
                                description "none";
                            }
                            container local-id {
                                uses local-id-and-class;
                                description "If the element is a localId (where the element above in the hierarchy must be the context in which the specific localId is relevant).";
                            }
                            leaf uuid {
                                type universal-id;
                                description "If the element is a uuid (where this element could be the top of a hierarchy but may also be at some level in the hierarchy where address navigation is considered necessary to assist in location of the UUID).";
                            }
                            container name {
                                uses name-and-class;
                                description "If the element is a name.";
                            }
                            leaf arbitrary-element {
                                type string;
                                description "Where the element is from some external model that is not formally represented in this model.";
                            }
                            description "One element of a hierarchy of elements.
                                Note that the element must have one and only one value chosen from a list of potential value types.";
                        }

                    /***********************
                    * package basic-conformant-operation
                    **********************/ 
                        /***********************
                        * package data-types
                        **********************/ 
                            typedef ActionVerbs {
                                type identityref {
                                    base action-verbs;
                                }
                                description "none";
                            }
                            typedef TestType {
                                type string;
                                description "none";
                            }

                        /***********************
                        * package object-classes
                        **********************/ 
                            grouping operation-envelope {
                                leaf operation-identifiers {
                                    type leafref {
                                        path '/core-model:operation-envelope/core-model:operation-identifiers/core-model:';
                                    }
                                    description "none";
                                }
                                leaf action-verb {
                                    type action-verbs;
                                    description "none";
                                }
                                description "none";
                            }
                            grouping operation-identifiers {
                                description "none";
                            }
                            grouping desired-outcome-constraints {
                                leaf-list outcome-element {
                                    type leafref {
                                        path '/core-model:desired-outcome-constraints/core-model:outcome-element/core-model:';
                                    }
                                    min-elements 1;
                                    description "none";
                                }
                                description "none";
                            }
                            grouping ltp {
                                description "none";
                            }
                            grouping outcome-element-constraints {
                                leaf specific-class-structure {
                                    type leafref {
                                        path '/core-model:specific-class-structure/core-model:';
                                    }
                                    description "none";
                                }
                                description "none";
                            }
                            grouping specific-class-structure {
                                leaf class-type-name {
                                    type leafref {
                                        path '/core-model:ltp/core-model:';
                                    }
                                    description "none";
                                }
                                description "none";
                            }
                            grouping specific-pattern {
                                description "none";
                            }





        /***********************
        * package synchronization-of-timing
        **********************/ 
            grouping clock {
                description "none";
            }

        /***********************
        * package profiles-templates-and-specifications-module
        **********************/ 
            /***********************
            * package spec-and-profile-sketch
            **********************/ 
                grouping any-entity-instance {
                    leaf-list profile {
                        type leafref {
                            path '/core-model:profile-instance/core-model:';
                        }
                        description "none";
                    }
                    leaf spec {
                        type leafref {
                            path '/core-model:spec-instance/core-model:';
                        }
                        description "none";
                    }
                    leaf class {
                        type leafref {
                            path '/core-model:any-entity-class/core-model:';
                        }
                        description "none";
                    }
                    description "none";
                }
                grouping profile-instance {
                    leaf spec-instance {
                        type leafref {
                            path '/core-model:spec-instance/core-model:';
                        }
                        description "none";
                    }
                    leaf profile-class {
                        type leafref {
                            path '/core-model:profile-class/core-model:';
                        }
                        description "none";
                    }
                    leaf class {
                        type leafref {
                            path '/core-model:any-entity-class/core-model:';
                        }
                        description "none";
                    }
                    description "none";
                }
                grouping spec-instance {
                    leaf spec-class {
                        type leafref {
                            path '/core-model:spec-class/core-model:';
                        }
                        description "none";
                    }
                    leaf class {
                        type leafref {
                            path '/core-model:any-entity-class/core-model:';
                        }
                        description "none";
                    }
                    description "none";
                }
                grouping any-entity-class {
                    description "none";
                }
                grouping spec-class {
                    uses any-entity-class;
                    description "none";
                }
                grouping profile-class {
                    uses any-entity-class;
                    description "none";
                }



    /***********************
    * package information-architecture-and-patterns
    **********************/ 
        /***********************
        * package patterns
        **********************/ 
            /***********************
            * package hypergraph
            **********************/ 
                grouping hypergraph {
                    leaf-list hyper-edge {
                        type leafref {
                            path '/core-model:hypergraph/core-model:hyper-edge/core-model:';
                        }
                        min-elements 1;
                        description "none";
                    }
                    leaf-list vertex {
                        type leafref {
                            path '/core-model:hypergraph/core-model:vertex/core-model:';
                        }
                        description "none";
                    }
                    description "none";
                }
                grouping hyper-edge {
                    leaf-list vertex {
                        type leafref {
                            path '/core-model:hypergraph/core-model:vertex/core-model:';
                        }
                        description "none";
                    }
                    description "none";
                }
                grouping vertex {
                    leaf-list hyper-edge {
                        type leafref {
                            path '/core-model:hypergraph/core-model:hyper-edge/core-model:';
                        }
                        min-elements 1;
                        description "none";
                    }
                    description "none";
                }
                grouping class-1 {
                    description "none";
                }

            /***********************
            * package constrained-hypergraph
            **********************/ 
                grouping constrained-hypergraph {
                    leaf-list constrained-hyper-edge {
                        type leafref {
                            path '/core-model:constrained-hypergraph/core-model:constrained-hyper-edge/core-model:';
                        }
                        min-elements 1;
                        description "none";
                    }
                    leaf-list constrained-vertex {
                        type leafref {
                            path '/core-model:constrained-hypergraph/core-model:constrained-vertex/core-model:';
                        }
                        description "none";
                    }
                    description "none";
                }
                grouping constrained-hyper-edge {
                    leaf-list constrained-vertex {
                        type leafref {
                            path '/core-model:constrained-hypergraph/core-model:constrained-vertex/core-model:';
                        }
                        description "none";
                    }
                    leaf-list vertex-opportunity {
                        type leafref {
                            path '/core-model:constrained-hypergraph/core-model:constrained-hyper-edge/core-model:vertex-opportunity/core-model:';
                        }
                        min-elements 1;
                        description "none";
                    }
                    description "none";
                }
                grouping constrained-vertex {
                    leaf-list constrained-hyper-edge {
                        type leafref {
                            path '/core-model:constrained-hypergraph/core-model:constrained-hyper-edge/core-model:';
                        }
                        min-elements 2;
                        max-elements 2;
                        description "none";
                    }
                    leaf-list vertexopportunity {
                        type leafref {
                            path '/core-model:constrained-hypergraph/core-model:constrained-hyper-edge/core-model:vertex-opportunity/core-model:';
                        }
                        min-elements 2;
                        max-elements 2;
                        description "none";
                    }
                    description "none";
                }
                grouping vertex-opportunity {
                    leaf constrainedvertex {
                        type leafref {
                            path '/core-model:constrained-hypergraph/core-model:constrained-vertex/core-model:';
                        }
                        description "none";
                    }
                    description "none";
                }

            /***********************
            * package hypergraph-recursive-constrained-hypergraph
            **********************/ 
                grouping constrained-hypergraph {
                    leaf-list constrained-hyper-edge {
                        type leafref {
                            path '/core-model:constrained-hyper-edge/core-model:';
                        }
                        min-elements 1;
                        description "none";
                    }
                    leaf-list constrained-vertex {
                        type leafref {
                            path '/core-model:constrained-vertex/core-model:';
                        }
                        description "none";
                    }
                    leaf-list vertex-opportunity {
                        type leafref {
                            path '/core-model:constrained-hyper-edge/core-model:vertex-opportunity/core-model:';
                        }
                        description "none";
                    }
                    leaf-list constrained-hyper-edge-view {
                        type leafref {
                            path '/core-model:constrained-hyper-edge/core-model:';
                        }
                        description "none";
                    }
                    description "none";
                }
                grouping constrained-hyper-edge {
                    leaf-list vertex-opportunity {
                        type leafref {
                            path '/core-model:constrained-hyper-edge/core-model:vertex-opportunity/core-model:';
                        }
                        min-elements 1;
                        description "none";
                    }
                    description "none";
                }
                grouping constrained-vertex {
                    leaf-list vertexopportunity {
                        type leafref {
                            path '/core-model:constrained-hyper-edge/core-model:vertex-opportunity/core-model:';
                        }
                        min-elements 2;
                        max-elements 2;
                        description "none";
                    }
                    description "none";
                }
                grouping vertex-opportunity {
                    leaf constrainedvertex {
                        type leafref {
                            path '/core-model:constrained-vertex/core-model:';
                        }
                        description "none";
                    }
                    leaf-list vertex-opportunity {
                        type leafref {
                            path '/core-model:constrained-hyper-edge/core-model:vertex-opportunity/core-model:';
                        }
                        description "none";
                    }
                    description "none";
                }

            /***********************
            * package recursive-constrained-hypergraph-with-implicit-vertex
            **********************/ 
                grouping constrained-hypergraph {
                    leaf-list constrained-hyper-edge {
                        type leafref {
                            path '/core-model:constrained-hyper-edge/core-model:';
                        }
                        min-elements 1;
                        description "none";
                    }
                    leaf-list vertex-opportunity {
                        type leafref {
                            path '/core-model:constrained-hyper-edge/core-model:vertex-opportunity/core-model:';
                        }
                        description "none";
                    }
                    leaf-list constrained-hyper-edge-view {
                        type leafref {
                            path '/core-model:constrained-hyper-edge/core-model:';
                        }
                        description "none";
                    }
                    description "none";
                }
                grouping constrained-hyper-edge {
                    leaf-list vertex-opportunity {
                        type leafref {
                            path '/core-model:constrained-hyper-edge/core-model:vertex-opportunity/core-model:';
                        }
                        min-elements 1;
                        description "none";
                    }
                    description "none";
                }
                grouping vertex-opportunity {
                    leaf-list vertex-opportunity {
                        type leafref {
                            path '/core-model:constrained-hyper-edge/core-model:vertex-opportunity/core-model:';
                        }
                        description "none";
                    }
                    leaf vertex-opportunity {
                        type leafref {
                            path '/core-model:constrained-hyper-edge/core-model:vertex-opportunity/core-model:';
                        }
                        description "none";
                    }
                    description "none";
                }

            /***********************
            * package recasting-recursive-hypergraph-as-component-system
            **********************/ 
                grouping system-hypergraph {
                    leaf-list component {
                        type leafref {
                            path '/core-model:component-hyper-edge/core-model:';
                        }
                        min-elements 1;
                        description "none";
                    }
                    leaf-list port {
                        type leafref {
                            path '/core-model:component-hyper-edge/core-model:port/core-model:';
                        }
                        description "none";
                    }
                    leaf-list opaque-component-view {
                        type leafref {
                            path '/core-model:component-hyper-edge/core-model:';
                        }
                        description "none";
                    }
                    description "none";
                }
                grouping component-hyper-edge {
                    leaf-list port {
                        type leafref {
                            path '/core-model:component-hyper-edge/core-model:port/core-model:';
                        }
                        min-elements 1;
                        description "none";
                    }
                    description "none";
                }
                grouping port-vertex-opportunity {
                    leaf-list view-port {
                        type leafref {
                            path '/core-model:component-hyper-edge/core-model:port/core-model:';
                        }
                        description "none";
                    }
                    leaf port {
                        type leafref {
                            path '/core-model:component-hyper-edge/core-model:port/core-model:';
                        }
                        description "none";
                    }
                    leaf direction {
                        type direction;
                        description "none";
                    }
                    description "none";
                }

            /***********************
            * package directed-implicit-vertex
            **********************/ 
                grouping constrained-hypergraph {
                    leaf-list constrained-hyper-edge {
                        type leafref {
                            path '/core-model:constrained-hyper-edge/core-model:';
                        }
                        min-elements 1;
                        description "none";
                    }
                    leaf-list vertex-opportunity {
                        type leafref {
                            path '/core-model:constrained-hyper-edge/core-model:vertex-opportunity/core-model:';
                        }
                        description "none";
                    }
                    leaf constrained-hyper-edge {
                        type leafref {
                            path '/core-model:constrained-hyper-edge/core-model:';
                        }
                        description "none";
                    }
                    description "none";
                }
                grouping constrained-hyper-edge {
                    leaf-list vertex-opportunity {
                        type leafref {
                            path '/core-model:constrained-hyper-edge/core-model:vertex-opportunity/core-model:';
                        }
                        min-elements 1;
                        description "none";
                    }
                    description "none";
                }
                grouping vertex-opportunity {
                    leaf-list vertex-opportunity {
                        type leafref {
                            path '/core-model:constrained-hyper-edge/core-model:vertex-opportunity/core-model:';
                        }
                        description "none";
                    }
                    leaf vertex-opportunity {
                        type leafref {
                            path '/core-model:constrained-hyper-edge/core-model:vertex-opportunity/core-model:';
                        }
                        description "none";
                    }
                    leaf direction {
                        type direction;
                        description "none";
                    }
                    description "none";
                }
                typedef Direction {
                    type identityref {
                        base direction;
                    }
                    description "none";
                }

            /***********************
            * package constrained-directed-hypergraph
            **********************/ 
                /***********************
                * package object-classes
                **********************/ 
                    grouping constrained-hyper-edge {
                        leaf-list constrained-vertex {
                            type leafref {
                                path '/core-model:constrained-hypergraph/core-model:constrained-vertex/core-model:';
                            }
                            description "none";
                        }
                        leaf-list vertex-opportunity {
                            type leafref {
                                path '/core-model:constrained-hypergraph/core-model:constrained-hyper-edge/core-model:vertex-opportunity/core-model:';
                            }
                            min-elements 1;
                            description "none";
                        }
                        description "none";
                    }
                    grouping constrained-hypergraph {
                        leaf-list constrained-hyper-edge {
                            type leafref {
                                path '/core-model:constrained-hypergraph/core-model:constrained-hyper-edge/core-model:';
                            }
                            min-elements 1;
                            description "none";
                        }
                        leaf-list constrained-vertex {
                            type leafref {
                                path '/core-model:constrained-hypergraph/core-model:constrained-vertex/core-model:';
                            }
                            description "none";
                        }
                        description "none";
                    }
                    grouping constrained-vertex {
                        leaf-list constrained-hyper-edge {
                            type leafref {
                                path '/core-model:constrained-hypergraph/core-model:constrained-hyper-edge/core-model:';
                            }
                            min-elements 2;
                            max-elements 2;
                            description "none";
                        }
                        leaf-list vertexopportunity {
                            type leafref {
                                path '/core-model:constrained-hypergraph/core-model:constrained-hyper-edge/core-model:vertex-opportunity/core-model:';
                            }
                            min-elements 2;
                            max-elements 2;
                            description "none";
                        }
                        description "none";
                    }
                    grouping vertex-opportunity {
                        leaf constrainedvertex {
                            type leafref {
                                path '/core-model:constrained-hypergraph/core-model:constrained-vertex/core-model:';
                            }
                            description "none";
                        }
                        leaf direction {
                            type direction;
                            description "none";
                        }
                        description "none";
                    }




}
