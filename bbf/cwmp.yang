module tr-181-2-13-0-usp-full {
  yang-version 1.1;

  namespace
    "urn:telekom:tbd";

  prefix bbfd-something;

  import ietf-yang-types {
    prefix yang;
  }

  import ietf-inet-types {
    prefix inet;
  }

  organization
    "TBD";

  contact
    "TBD";

  description
    "TBD";

  revision 1970-01-01 {
    description
      "TBD";
    reference
      "TBD";
  }

  typedef Alias {
    description
    "* The CPE MUST NOT change the parameter value.";
    type string;
  }
  typedef Dbm1000 {
    description
    "The value is measured in ''dBm/1000'', i.e.  the value
    divided by 1000 is dB relative to 1 mW.  For example,
    -12345 means -12.345 dBm, 0 means 0 dBm (1 mW) and 12345
    means 12.345 dBm.";
    type int32;
  }
  typedef DiagnosticsState {
    description
    "While the test is in progress, setting this parameter to
    {{enum|Canceled}} MUST result in the test being canceled
    and the value of this parameter being set to {{enum|None}}.
    If the CPE does not support the {{enum|Canceled}} value, it
    MUST return a SPV error with \"Invalid Parameter value\"
    (9007) to the ACS instead.";
    type string;
  }
  typedef IEEE_EUI64 {
    description
    "* The extension identifier (40 bits for OUI-24 or 28 bits
    for OUI-36) assigned by the organization with that
    company_id assignment.";
    type string;
  }
  typedef JSONObject {
    description
    "A JSON Object as defined in {{bibref|RFC7159|Section 4}}.";
    type string;
  }
  typedef ZigBeeNetworkAddress {
    description
    "The ZigBee 16-bit network address (NWK) as defined in
    {{bibref|ZigBee2007}}. The address is assigned to a device
    by the network layer and used by the network layer for
    routing messages between devices.";
    type string;
  }
  typedef PSMBreakPointIndexAndLevel {
    description
    "{{bibref|G.9964|Clause 5.2}} defines limits on PSM
    breakpoint levels.";
    type uint32;
  }
  container Device {
    description
    "The top-level object for a Device.";
    leaf RootDataModelVersion {
      config false;
      description
      "Root data model version, e.g.  ''2.4''.  For a
      vendor-defined root data model, this is the standard
      Broadband Forum model on which the vendor-defined model
      is based.";
      type string {
        length "0..32";
        pattern "2\\.\\d+";
      }
    }
    leaf InterfaceStackNumberOfEntries {
      config false;
      description
      "{{numentries}}";
      type uint32;
    }
    container Services {
      description
      "This object contains general services information.";
    }
    container DeviceInfo {
      description
      "This object contains general device information.";
      leaf-list DeviceCategory {
        config false;
        description
        "Note: It is assumed that this list might be used for
        HTIP (Home-network Topology Identifying Protocol)
        {{bibref|JJ-300.00}} and {{bibref|G.9973}}. Standard
        HTIP device categories are defined in
        {{bibref|JJ-300.01}}. In this case, the maximum length
        of the list is 127 and of each item is 31, and any
        non-HTIP device categories SHOULD NOT conflict with
        standard HTIP device categories.";
        type string;
      }
      leaf Manufacturer {
        config false;
        description
        "The manufacturer of the CPE (human readable string).";
        type string {
          length "0..64";
        }
      }
      leaf ManufacturerOUI {
        config false;
        description
        "Any change would indicate that it's a new device and
        would therefore require a BOOTSTRAP Inform.";
        type string {
          length "6";
          pattern "[0-9A-F]{6}";
        }
      }
      leaf SupportedDataModelNumberOfEntries {
        config false;
        description
        "{{numentries}}";
        type uint32;
      }
      leaf ModelName {
        config false;
        description
        "Model name of the CPE (human readable string).";
        type string {
          length "0..64";
        }
      }
      leaf ModelNumber {
        config false;
        description
        "Note: It is assumed that this string might be used for
        HTIP (Home-network Topology Identifying Protocol)
        {{bibref|JJ-300.00}} and {{bibref|G.9973}}. In this
        case, the maximum length of the string is 31.";
        type string {
          length "0..64";
        }
      }
      leaf Description {
        config false;
        description
        "A full description of the CPE device (human readable
        string).";
        type string {
          length "0..256";
        }
      }
      leaf ProductClass {
        config false;
        description
        "This value MUST remain fixed over the lifetime of the
        device, including across firmware updates.  Any change
        would indicate that it's  a new device and would
        therefore require a BOOTSTRAP Inform.";
        type string {
          length "0..64";
        }
      }
      leaf SerialNumber {
        config false;
        description
        "This value MUST remain fixed over the lifetime of the
        device, including across firmware updates.  Any change
        would indicate that it's  a new device and would
        therefore require a BOOTSTRAP Inform.";
        type string {
          length "0..64";
        }
      }
      leaf HardwareVersion {
        config false;
        description
        "A string identifying the particular CPE model and
        version.";
        type string {
          length "0..64";
        }
      }
      leaf SoftwareVersion {
        config false;
        description
        "For CPEs that support multiple firmware images, the
        value for this parameter MUST be the software version
        of the active firmware image.";
        type string {
          length "0..64";
        }
      }
      leaf ActiveFirmwareImage {
        config false;
        description
        "{{noreference}}A full path reference to the row in the
        {{object|FirmwareImage}} table representing the
        currently running firmware image.";
        type string;
      }
      leaf BootFirmwareImage {
        config true;
        description
        "In situations where the CPE cannot boot the firmware
        image specified by this parameter and manages to boot a
        different firmware image, the CPE MUST NOT modify this
        value to point to the alternate firmware image that is
        currently active.";
        type string;
      }
      leaf-list AdditionalHardwareVersion {
        config false;
        description
        "{{list}}  Each entry is an additional version.
        Represents any additional hardware version information
        the vendor might wish to supply.";
        type string;
      }
      leaf-list AdditionalSoftwareVersion {
        config false;
        description
        "{{list}}  Each entry is an additional version.
        Represents any additional software version information
        the vendor might wish to supply.";
        type string;
      }
      leaf ProvisioningCode {
        config true;
        description
        "Identifier of the primary service provider and other
        provisioning information, which MAY be used by the ACS
        to  determine service provider-specific customization
        and provisioning parameters.";
        type string {
          length "0..64";
        }
      }
      leaf UpTime {
        config false;
        description
        "Time in {{units}} since the CPE was last restarted.";
        type uint32;
      }
      leaf FirstUseDate {
        config false;
        description
        "If NTP or equivalent is not available, this parameter,
        if present, SHOULD be set to the Unknown Time value.";
        type yang:date-and-time;
      }
      leaf FirmwareImageNumberOfEntries {
        config false;
        description
        "{{numentries}}";
        type uint32;
      }
      leaf VendorConfigFileNumberOfEntries {
        config false;
        description
        "{{numentries}}";
        type uint32;
      }
      leaf ProcessorNumberOfEntries {
        config false;
        description
        "{{numentries}}";
        type uint32;
      }
      leaf VendorLogFileNumberOfEntries {
        config false;
        description
        "{{numentries}}";
        type uint32;
      }
      leaf LocationNumberOfEntries {
        config false;
        description
        "{{numentries}}";
        type uint32;
      }
      leaf DeviceImageNumberOfEntries {
        config false;
        description
        "{{numentries}}";
        type uint32;
      }
      list VendorConfigFile {
        key "Name";
        unique "Alias";
        config true;
        description
        "Whenever the CPE successfully downloads a configuration
        file as a result of the Download RPC with the FileType
        argument of ''3 Vendor Configuration File'', the CPE
        MUST update this table.";
        leaf Alias {
          config true;
          description
          "{{datatype|expand}}";
          type Alias;
        }
        leaf Name {
          config true;
          description
          "Otherwise, the value of this parameter MUST be set to
          the value of the TargetFileName argument of the
          Download RPC used to download this configuration
          file.";
          type string {
            length "0..64";
          }
        }
        leaf Version {
          config false;
          description
          "Otherwise, the value of this parameter MUST be
          {{empty}}.";
          type string {
            length "0..16";
          }
        }
        leaf Date {
          config false;
          description
          "Date and time when the content of the current version
          of this vendor configuration file was first applied
          by the CPE.";
          type yang:date-and-time;
        }
        leaf Description {
          config false;
          description
          "A description of the vendor configuration file
          (human-readable string).";
          type string {
            length "0..256";
          }
        }
        leaf UseForBackupRestore {
          config false;
          description
          "Note: The backup and restore operations may require
          the use of multiple {{object}} instances.  In this
          scenario the mechanism for detemining the order and
          combination of {{object}} instances used for backup
          and restoration purposes is implementation specific.";
          type boolean;
        }
      }
      container MemoryStatus {
        description
        "Status of the device's volatile physical memory.";
        leaf Total {
          config false;
          description
          "The total physical RAM, in {{units}}, installed on
          the device.";
          type uint32;
        }
        leaf Free {
          config false;
          description
          "The free physical RAM, in {{units}}, currently
          available on the device.";
          type uint32;
        }
      }
      container ProcessStatus {
        description
        "Status of the processes on the device.";
        leaf CPUUsage {
          config false;
          description
          "The total amount of the CPU, in {{units}}, rounded up
          to the nearest whole {{units}}.  In the case that
          multiple CPU are present, this value represents the
          average of all CPU.";
          type uint32 {
            range "min..100";
          }
        }
        leaf ProcessNumberOfEntries {
          config false;
          description
          "Since a Process can come and go very quickly, the CPE
          SHOULD place a locally specified limit on the
          frequency at which it will notify the ACS of value
          changes, as described in {{bibref|TR-069a2|Section
          3.2.1}}.";
          type uint32;
        }
        list Process {
          key "PID";
          config false;
          description
          "List of all processes running on the device.";
          leaf PID {
            config false;
            description
            "The Process Identifier.";
            type uint32;
          }
          leaf Command {
            config false;
            description
            "The name of the command that has caused the process
            to exist.";
            type string {
              length "0..256";
            }
          }
          leaf Size {
            config false;
            description
            "The size in {{units}} of the memory occupied by the
            process.";
            type uint32;
          }
          leaf Priority {
            config false;
            description
            "The priority of the process where 0 is highest.";
            type uint32 {
              range "min..99";
            }
          }
          leaf CPUTime {
            config false;
            description
            "The amount of time in {{units}} that the process
            has spent taking up CPU time since the process was
            started.";
            type uint32;
          }
          leaf State {
            config false;
            description
            "The current state that the process is in.";
            type enumeration {
              enum "Running";
              enum "Sleeping";
              enum "Stopped";
              enum "Idle";
              enum "Uninterruptible";
              enum "Zombie";
            }
          }
        }
      }
      container TemperatureStatus {
        description
        "Status of the temperature of the device.";
        leaf TemperatureSensorNumberOfEntries {
          config false;
          description
          "{{numentries}}";
          type uint32;
        }
        list TemperatureSensor {
          key "Name";
          unique "Alias";
          config true;
          description
          "This object represents information that the device
          has obtained via sampling an internal temperature
          sensor.";
          leaf Alias {
            config true;
            description
            "{{datatype|expand}}";
            type Alias;
          }
          leaf Enable {
            config true;
            description
            "Indicates whether or not the temperature sensor is
            enabled.";
            type boolean;
          }
          leaf Status {
            config false;
            description
            "The status of this temperature sensor.";
            type enumeration {
              enum "Disabled" {
                description
                "The sensor is not currently sampling the
                temperature.";
              }
              enum "Enabled" {
                description
                "The sensor is currently sampling the
                temperature.";
              }
              enum "Error" {
                description
                "The sensor error currently prevents sampling
                the temperature.";
              }
            }
          }
          leaf Reset {
            config true;
            description
            "When set to {{true}}, resets the temperature
            sensor.";
            type boolean;
          }
          leaf ResetTime {
            config false;
            description
            "The Unknown Time value, as defined in
            {{bibref|TR-106a2}}, indicates that this
            temperature sensor has never been reset, which can
            only happen if it has never been enabled.";
            type yang:date-and-time;
          }
          leaf Name {
            config true;
            description
            "Name of this temperature sensor.  This text MUST be
            sufficient to distinguish this temperature sensor
            from other temperature sensors.";
            type string {
              length "0..256";
            }
          }
          leaf Value {
            config false;
            description
            "A value of -274 (which is below absolute zero)
            indicates a good reading has not been obtained
            since last reset.";
            type int32 {
              range "-274..max";
            }
          }
          leaf LastUpdate {
            config false;
            description
            "The Unknown Time value, as defined in
            {{bibref|TR-106a2}}, indicates a good reading has
            not been obtained since last reset.";
            type yang:date-and-time;
          }
          leaf MinValue {
            config false;
            description
            "A value of -274 (which is below absolute zero)
            indicates a good reading has not been obtained
            since last reset.";
            type int32 {
              range "-274..max";
            }
          }
          leaf MinTime {
            config false;
            description
            "The Unknown Time value, as defined in
            {{bibref|TR-106a2}}, indicates a good reading has
            not been obtained since last reset.";
            type yang:date-and-time;
          }
          leaf MaxValue {
            config false;
            description
            "A value of -274 (which is below absolute zero)
            indicates a good reading has not been obtained
            since last reset.";
            type int32 {
              range "-274..max";
            }
          }
          leaf MaxTime {
            config false;
            description
            "The Unknown Time value, as defined in
            {{bibref|TR-106a2}}, indicates a good reading has
            not been obtained since last reset.";
            type yang:date-and-time;
          }
          leaf LowAlarmValue {
            config true;
            description
            "A change to this value will cause
            {{param|LowAlarmTime}} to be reset.";
            type int32 {
              range "-274..max";
            }
          }
          leaf LowAlarmTime {
            config false;
            description
            "The Unknown Time value, as defined in
            {{bibref|TR-106a2}}, indicates that an alarm has
            not been encountered since the last reset.";
            type yang:date-and-time;
          }
          leaf HighAlarmValue {
            config true;
            description
            "A change to this value will cause
            {{param|HighAlarmTime}} to be reset.";
            type int32 {
              range "-274..max";
            }
          }
          leaf PollingInterval {
            config true;
            description
            "If the value is greater than 0 then the device MUST
            use this value as the polling interval.";
            type uint32;
          }
          leaf HighAlarmTime {
            config false;
            description
            "The Unknown Time value, as defined in
            {{bibref|TR-106a2}}, indicates that an alarm has
            not been encountered since the last reset.";
            type yang:date-and-time;
          }
        }
      }
      container NetworkProperties {
        description
        "This object defines the parameters that describe how
        the device handles network traffic.";
        leaf MaxTCPWindowSize {
          config false;
          description
          "The maximum number of {{units}} of outstanding data a
          sender can send on a particular connection prior to
          an acknowledgment {{bibref|RFC793}}.  Any scaling
          factor SHOULD be included in this parameter
          {{bibref|RFC1323}}.";
          type uint32;
        }
        leaf-list TCPImplementation {
          config false;
          description
          "Tahoe, Reno, and New Reno are defined in
          {{bibref|RFC2582}}";
          type enumeration {
            enum "Tahoe" {
              description
              "Represents the base TCP implementation in
              {{bibref|RFC793}} and elements of
              {{bibref|RFC2582}}";
            }
            enum "Reno" {
              description
              "Represents the base TCP implementation in
              {{bibref|RFC793}} with the additional algorithms
              defined in {{bibref|RFC2581}}";
            }
            enum "New Reno" {
              description
              "Described as a modification to the Reno
              algorithms in {{bibref|RFC2582}}";
            }
            enum "Vegas" {
              description
              "An emerging TCP congestion control mechanism";
            }
          }
        }
      }
      list Processor {
        key "Alias";
        config true;
        description
        "Each table entry represents a hardware or virtual
        processor that resides on this device.";
        leaf Alias {
          config true;
          description
          "{{datatype|expand}}";
          type Alias;
        }
        leaf Architecture {
          config false;
          description
          "For processor architectures not included in this
          list, the vendor MAY include vendor-specific values,
          which MUST use the format defined in
          {{bibref|TR-106a4|Section 3.3}}.";
          type enumeration {
            enum "arm";
            enum "i386";
            enum "m68010";
            enum "m68k";
            enum "mipseb" {
              description
              "big-endian";
            }
            enum "mipsel" {
              description
              "little-endian";
            }
            enum "powerpc";
            enum "sh3eb" {
              description
              "big-endian";
            }
            enum "sh3el" {
              description
              "little-endian";
            }
            enum "x86_64";
          }
        }
      }
      list VendorLogFile {
        key "Name";
        unique "Alias";
        config true;
        description
        "This table of log files is informational only and does
        not allow the ACS to operate on these files in any way.";
        leaf Alias {
          config true;
          description
          "{{datatype|expand}}";
          type Alias;
        }
        leaf Name {
          config true;
          description
          "Typically this will be the full file system path, but
          provided that it is guaranteed to be unique across
          current and future log files, it MAY be a shorter
          name derived from the file system path, or be derived
          via another mechanism.";
          type string {
            length "0..64";
          }
        }
        leaf MaximumSize {
          config false;
          description
          "The maximum size of the log file in {{units}}.  If
          the device doesn't know the maximum file size then
          {{param}} will be 0.";
          type uint32;
        }
        leaf Persistent {
          config false;
          description
          "When {{false}}, the log file contents will be purged
          when the device is rebooted.";
          type boolean;
        }
      }
      list Location {
        key "Source ExternalSource";
        config true;
        description
        "This object contains Location information.";
        leaf Source {
          config true;
          description
          "Identifies the source of the location data.";
          type enumeration {
            enum "GPS";
            enum "AGPS";
            enum "Manual";
            enum "External";
          }
        }
        leaf AcquiredTime {
          config false;
          description
          "The time when the location was acquired.";
          type yang:date-and-time;
        }
        leaf ExternalSource {
          config true;
          description
          "If {{param|ExternalProtocol}} has a value of
          {{enum|CWMP|ExternalProtocol}},  this is the URL or
          IP address of the ACS.";
          type string;
        }
        leaf ExternalProtocol {
          config false;
          description
          "Meaningful only if {{param|Source}} has a value of
          {{enum|External|Source}}, otherwise it MUST be
          {{empty}}.";
          type enumeration {
            enum "<empty>" {
              description
              "{{empty}}";
            }
            enum "CWMP";
            enum "OMA-DM";
            enum "SNMP";
            enum "UPnP";
            enum "HELD";
            enum "DHCPv4";
            enum "DHCPv6";
            enum "LLDP-MED";
            enum "MLP";
            enum "Other";
          }
          default "CWMP";
        }
        leaf DataObject {
          config true;
          description
          "Only zero or one Location object instance with value
          {{enum|CWMP|ExternalProtocol}} MUST exist at any
          given time.";
          type string {
            length "0..1200";
          }
        }
      }
      list DeviceImageFile {
        key "Location";
        unique "Alias";
        config true;
        description
        "This object describes an image of the device.";
        leaf Alias {
          config true;
          description
          "{{datatype|expand}}";
          type Alias;
        }
        leaf Location {
          config true;
          description
          "The location of the device that represents the image
          as the user looks at the front of the device in its
          typical orientation (e.g., on-end, flat).";
          type enumeration {
            enum "Front";
            enum "Back";
            enum "Left";
            enum "Right";
            enum "Top";
            enum "Bottom";
          }
        }
        leaf Image {
          config false;
          description
          "The device image in PNG, JPEG or GIF format.";
          type binary;
        }
      }
      list FirmwareImage {
        key "Alias";
        config true;
        description
        "This is a static table – the number of object instances
        in this table is defined by the firmware that is
        currently running.";
        leaf Alias {
          config true;
          description
          "{{datatype|expand}}";
          type Alias;
        }
        leaf Name {
          config false;
          description
          "The value of {{param}} is {{empty}} if
          {{param|Status}} is anything other than
          {{enum|Available|Status}},
          {{enum|InstallationFailed|Status}}, or
          {{enum|ActivationFailed|Status}}.";
          type string {
            length "0..64";
          }
        }
        leaf Version {
          config false;
          description
          "The value of {{param}} is {{empty}} if
          {{param|Status}} is anything other than
          {{enum|Available|Status}},
          {{enum|InstallationFailed|Status}}, or
          {{enum|ActivationFailed|Status}}.";
          type string {
            length "0..64";
          }
        }
        leaf Available {
          config true;
          description
          "Firmware image instances cannot be deleted, so a
          Controller MAY use this parameter to subsequently
          mark a particular firmware as being invalid, which
          will prevent the Agent from attempting to boot it.";
          type boolean;
        }
        leaf Status {
          config false;
          description
          "Status of the firmware image, as determined by the
          Agent.  {{enum}}";
          type enumeration {
            enum "NoImage" {
              description
              "This value could happen on an Agent that supports
              multiple firmware images, but only has a single
              image installed.";
            }
            enum "Downloading" {
              description
              "This Firmware Image instance is being downloaded.";
            }
            enum "Validating" {
              description
              "This Firmware Image instance has been downloaded,
              and is in the process of being validated.";
            }
            enum "Available" {
              description
              "This Firmware Image instance has been downloaded,
              validated, and installed, and is ready to be
              activated.";
            }
            enum "DownloadFailed" {
              description
              "The Agent has attempted to download this Firmware
              Image instance, but ultimately failed while
              retrieving it from the source URL.";
            }
            enum "ValidationFailed" {
              description
              "The Agent has attempted to validate a Firmware
              Image downloaded to this instance, but ultimately
              failed while validating it.";
            }
            enum "InstallationFailed" {
              description
              "The Agent has attempted to install a Firmware
              Image downloaded and validated to this instance,
              but ultimately failed while installing it.";
            }
            enum "ActivationFailed" {
              description
              "The Agent has attempted to active this Firmware
              Image instance, but ultimately failed while being
              activated.";
            }
          }
        }
        leaf BootFailureLog {
          config false;
          description
          "The length of this string is defined as
          implementation-specific by the Agent.";
          type string;
        }
      }
      list SupportedDataModel {
        key "URL";
        unique "Alias";
        unique "UUID";
        config true;
        description
        "Considering that every device has some form of a data
        model, this table MUST NOT be empty.";
        leaf Alias {
          config true;
          description
          "{{datatype|expand}}";
          type Alias;
        }
        leaf URL {
          config true;
          description
          "Behavior in the event of an invalid URL, failure to
          access the referenced XML file, or an invalid XML
          file, is implementation-dependent.";
          type string {
            length "0..256";
          }
        }
        leaf UUID {
          config false;
          description
          "UUID ({{bibref|RFC4122}}) that is the value of the
          uuid attribute in the DT Instance referenced by
          {{param|URL}}.";
          type yang:uuid;
        }
        leaf URN {
          config false;
          description
          "For example, if this table entry references a DT
          Instance that refers to the ''Device:1.3'' Root
          Object, the value of this parameter would be
          ''urn:broadband-forum-org:tr-157-1-0-0'', because
          TR-157 defines ''Device:1.3''.  If the DT Instance
          instead referred to a vendor-specific Root Object,
          e.g.  ''X_EXAMPLE_Device:1.0'' (derived from
          ''Device:1.3''), the value of this parameter would be
          something like ''urn:example-com:device-1-0-0''.";
          type string {
            length "0..256";
          }
        }
        leaf-list Features {
          config false;
          description
          "then the value of this parameter might be
          ''DNSServer,Router,X_MyDeviceFeature''.  The order in
          which the features are listed is not significant.";
          type string;
        }
      }
      container ProxierInfo {
        description
        "Represents the associated CPE Proxier for a Proxied
        Device that utilizes the Virtual CWMP Device Mechanism
        {{bibref|TR-069a4|Annex J.1.1}}.";
        leaf ManufacturerOUI {
          config false;
          description
          "The value MUST be a valid OUI as defined in
          {{bibref|OUI}}.";
          type string {
            length "6";
            pattern "[0-9A-F]{6}";
          }
        }
        leaf ProductClass {
          config false;
          description
          "{{empty}} indicates either that the CPE Proxier does
          not use a product class to differentiate its serial
          number.";
          type string {
            length "0..64";
          }
        }
        leaf SerialNumber {
          config false;
          description
          "Serial number of the associated CPE Proxier.";
          type string {
            length "0..64";
          }
        }
        leaf ProxyProtocol {
          config false;
          description
          "Vendors can extend the enumerated values with vendor
          specific extensions, in which case the rules outlined
          in {{bibref|TR-106a6|3.3}} MUST be adhered to.";
          type enumeration {
            enum "Z-Wave" {
              description
              "see {{bibref|Z-Wave}}";
            }
            enum "ZigBee" {
              description
              "see {{bibref|ZigBee}}";
            }
            enum "UPnP-DM" {
              description
              "see {{bibref|UPnP-DM:1}}";
            }
            enum "ETSI-M2M" {
              description
              "see {{bibref|ETSIM2MFA}}";
            }
          }
        }
      }
    }
    container ManagementServer {
      description
      "This object contains parameters relating to the CPE's
      association with an ACS.";
      leaf EnableCWMP {
        config true;
        description
        "The subscriber can re-enable the CPE's CWMP support
        either by performing a factory reset or by using a
        LAN-side protocol to change  the value of this
        parameter back to {{true}}.";
        type boolean;
        default "true";
      }
      leaf URL {
        config true;
        description
        "Note that on a factory reset of the CPE, the value of
        this parameter might be reset to its factory value.  If
        an ACS modifies the  value of this parameter, it SHOULD
        be prepared to accommodate the situation that the
        original value is restored as the result of a  factory
        reset.";
        type string {
          length "0..256";
        }
      }
      leaf Username {
        config true;
        description
        "Note that on a factory reset of the CPE, the value of
        this parameter might be reset to its factory value.  If
        an ACS modifies the  value of this parameter, it SHOULD
        be prepared to accommodate the situation that the
        original value is restored as the result of a  factory
        reset.";
        type string {
          length "0..256";
        }
      }
      leaf Password {
        config true;
        description
        "Note that on a factory reset of the CPE, the value of
        this parameter might be reset to its factory value.  If
        an ACS modifies the  value of this parameter, it SHOULD
        be prepared to accommodate the situation that the
        original value is restored as the result of a  factory
        reset.";
        type string {
          length "0..256";
        }
      }
      leaf ScheduleReboot {
        config true;
        description
        "If the value specifies a date and time that has already
        passed (i.e., a past date and time), no reboot will be
        performed.";
        type yang:date-and-time;
      }
      leaf DelayReboot {
        config true;
        description
        "Whenever the CPE reboots, this value MUST be reset by
        the CPE to -1.";
        type int32 {
          range "-1..max";
        }
      }
      leaf PeriodicInformEnable {
        config true;
        description
        "Whether or not the CPE MUST periodically send CPE
        information to the ACS using the Inform method  call.";
        type boolean;
      }
      leaf PeriodicInformInterval {
        config true;
        description
        "The duration in {{units}} of the interval for which the
        CPE MUST attempt to connect with the ACS and call the
        Inform method if {{param|PeriodicInformEnable}} is
        {{true}}.";
        type uint32 {
          range "1..max";
        }
      }
      leaf PeriodicInformTime {
        config true;
        description
        "If absolute time is not available to the CPE, its
        periodic Inform behavior MUST be the same as if the
        {{param}} parameter was set to the Unknown Time value.";
        type yang:date-and-time;
      }
      leaf ParameterKey {
        config false;
        description
        "The CPE MUST only modify the value of {{param}} as a
        result of SetParameterValues, AddObject, DeleteObject,
        or due to a factory  reset.  On factory reset, the
        value of {{param}} MUST be set to {{empty}}.";
        type string {
          length "0..32";
        }
      }
      leaf ConnectionRequestURL {
        config false;
        description
        "Note: If the ''host'' portion of the URL is a literal
        IPv6 address then it MUST be enclosed in square
        brackets (see {{bibref|RFC3986|Section 3.2.2}}).";
        type string {
          length "0..256";
        }
      }
      leaf ConnectionRequestUsername {
        config true;
        description
        "Username used to authenticate an ACS making a
        Connection Request to the CPE.";
        type string {
          length "0..256";
        }
      }
      leaf ConnectionRequestPassword {
        config true;
        description
        "Password used to authenticate an ACS making a
        Connection Request to the CPE.";
        type string {
          length "0..256";
        }
      }
      leaf UpgradesManaged {
        config true;
        description
        "Note that an autonomous upgrade (reported via an \"10
        AUTONOMOUS TRANSFER COMPLETE\" Inform Event code)
        SHOULD be regarded as a managed  upgrade if it is
        performed according to ACS-specified policy.";
        type boolean;
      }
      leaf KickURL {
        config false;
        description
        "LAN-accessible URL, as defined in {{bibref|RFC3986}},
        from which the CPE can be ''kicked'' to initiate the
        Kicked RPC method call.   MUST be an absolute URL
        including a host name or IP address as would be used on
        the LAN side of the CPE.";
        type string {
          length "0..256";
        }
      }
      leaf DownloadProgressURL {
        config false;
        description
        "LAN-accessible URL, as defined in {{bibref|RFC3986}},
        to which a web-server associated with the ACS MAY
        redirect a user's browser on  initiation of a file
        download to observer the status of the download.";
        type string {
          length "0..256";
        }
      }
      leaf DefaultActiveNotificationThrottle {
        config true;
        description
        "The time of the last session completion does not need
        to be tracked across reboots.";
        type uint32;
      }
      leaf CWMPRetryMinimumWaitInterval {
        config true;
        description
        "The device MUST use a random value between {{param}}
        and ({{param}} * {{param|CWMPRetryIntervalMultiplier}}
        / 1000) as the first  retry wait interval.  Other
        values in the retry pattern MUST be calculated using
        this value as a starting point.";
        type uint32 {
          range "1..65535";
        }
      }
      leaf CWMPRetryIntervalMultiplier {
        config true;
        description
        "The device MUST use a random value between
        {{param|CWMPRetryMinimumWaitInterval}}  and
        ({{param|CWMPRetryMinimumWaitInterval}} *  {{param}} /
        1000) as the first retry wait interval.  Other values
        in the retry pattern MUST be calculated using this
        value as a  starting point.";
        type uint32 {
          range "1000..65535";
        }
      }
      leaf HTTPConnectionRequestEnable {
        config true;
        description
        "If HTTP connection request handling is disabled
        ({{param}} is set to {{false}}),
        {{param|ConnectionRequestURL}} MUST be set to {{empty}}
        and the CPE MUST close the port used by the HTTP
        connection request server.";
        type boolean;
        default "true";
      }
      leaf UDPConnectionRequestAddress {
        config false;
        description
        "Note: If the ''host'' portion of the URL is a literal
        IPv6 address then it MUST be enclosed in square
        brackets (see {{bibref|RFC3986|Section 3.2.2}}).";
        type string {
          length "0..256";
        }
      }
      leaf STUNEnable {
        config true;
        description
        "Enables or disables the use of STUN by the CPE.  This
        applies only to the use of STUN in association with the
        ACS to allow UDP Connection Requests.";
        type boolean;
      }
      leaf STUNServerAddress {
        config true;
        description
        "If is {{empty}} and {{param|STUNEnable}} is {{true}},
        the CPE MUST use the address of the ACS extracted from
        the host portion of the  ACS URL.";
        type string {
          length "0..256";
        }
      }
      leaf STUNServerPort {
        config true;
        description
        "By default, this SHOULD be the equal to the default
        STUN port, 3478.";
        type uint32 {
          range "0..65535";
        }
      }
      leaf STUNUsername {
        config true;
        description
        "If is {{empty}}, the CPE MUST NOT send STUN Binding
        Requests with message integrity.";
        type string {
          length "0..256";
        }
      }
      leaf STUNPassword {
        config true;
        description
        "The value of the STUN Password to be used in computing
        the MESSAGE-INTEGRITY attribute to be used in Binding
        Requests (only if message integrity has been requested
        by the STUN server).";
        type string {
          length "0..256";
        }
      }
      leaf STUNMaximumKeepAlivePeriod {
        config true;
        description
        "A value of -1 indicates that no maximum period is
        specified.";
        type int32 {
          range "-1..max";
        }
      }
      leaf STUNMinimumKeepAlivePeriod {
        config true;
        description
        "If STUN Is enabled, the minimum period, in {{units}},
        that STUN Binding Requests can be sent by the CPE for
        the  purpose of maintaining the binding in the Gateway.
        This limit applies only to Binding Requests sent from
        the UDP Connection Request  address and port, and only
        those that do not contain the BINDING-CHANGE attribute.
        This limit does not apply to retransmissions  following
        the procedures defined in {{bibref|RFC3489}}.";
        type uint32;
      }
      leaf NATDetected {
        config false;
        description
        "When {{param|STUNEnable}} is {{false}}, this value MUST
        be {{false}}.";
        type boolean;
      }
      leaf AliasBasedAddressing {
        config false;
        description
        "A {{true}} value indicates that the CPE supports the
        Alias-Based Addressing Mechanism, as defined in
        {{bibref|TR-069a4|3.6.1}} and described in
        {{bibref|TR-069a4|Appendix II}}.";
        type boolean;
      }
      leaf InstanceMode {
        config true;
        description
        "This parameter is REQUIRED for any CPE supporting
        Alias-Based Addressing.";
        type enumeration {
          enum "InstanceNumber";
          enum "InstanceAlias";
        }
        default "InstanceNumber";
      }
      leaf AutoCreateInstances {
        config true;
        description
        "This parameter is REQUIRED for any CPE supporting
        Alias-Based Addressing.";
        type boolean;
        default "false";
      }
      leaf ManageableDeviceNumberOfEntries {
        config false;
        description
        "{{numentries}}";
        type uint32;
      }
      leaf ManageableDeviceNotificationLimit {
        config true;
        description
        "The minimum time, in seconds, between Active
        Notifications resulting from changes to the
        {{param|ManageableDeviceNumberOfEntries}} (if Active
        Notification is enabled).";
        type uint32;
      }
      leaf EmbeddedDeviceNumberOfEntries {
        config false;
        description
        "{{numentries}}";
        type uint32;
      }
      leaf VirtualDeviceNumberOfEntries {
        config false;
        description
        "{{numentries}}";
        type uint32;
      }
      leaf-list SupportedConnReqMethods {
        config false;
        description
        "The connection request methods supported by this
        {{object}}. {{enum}}";
        type enumeration {
          enum "HTTP" {
            description
            "The connection request method as specified in
            {{bibref|TR-069|Section 3.2.2 ACS Connection
            Initiation}}, '''REQUIRED'''";
          }
          enum "STUN" {
            description
            "The connection request method as specified in
            {{bibref|TR-069|Annex G Connection Request via NAT
            Gateway}}";
          }
          enum "XMPP" {
            description
            "The connection request method as specified in
            {{bibref|TR-069a5|Annex K XMPP Connection Request}}";
          }
        }
      }
      leaf ConnReqXMPPConnection {
        config true;
        description
        "{{reference|the {{object|.XMPP.Connection}} instance
        that is used for connection requests to this
        {{object}}}}";
        type string;
      }
      leaf-list ConnReqAllowedJabberIDs {
        config true;
        description
        "If this Parameter is {{empty}} then all Jabber IDs are
        allowed and an XMPP Connection Request can not be
        deemed invalid due to the \"from\" address.";
        type string {
          length "0..256";
        }
      }
      leaf ConnReqJabberID {
        config false;
        description
        "If the {{object|.XMPP.Connection}} instance being
        referenced by the {{param|ConnReqXMPPConnection}}
        parameter is lost
        ({{param|.XMPP.Connection.{i}.Status}} parameter
        changes from Enabled to some other value), then the
        value of this parameter MUST remain unchanged until the
        connection can be reestablished and a new
        {{param|.XMPP.Connection.{i}.JabberID}} can be
        established.  If the new
        {{param|.XMPP.Connection.{i}.JabberID}} is identical to
        the existing value, then the value of this parameter
        MUST NOT be altered and a VALUE CHANGE event MUST NOT
        be generated.";
        type string;
      }
      leaf-list HTTPCompressionSupported {
        config false;
        description
        "Vendors can extend the enumerated values with vendor
        specific extensions, in which case the rules outlined
        in {{bibref|TR-106a7|Section 3.3}} MUST be adhered to.";
        type enumeration {
          enum "GZIP" {
            description
            "As defined in {{bibref|RFC2616|Section 3.5}}";
          }
          enum "Compress" {
            description
            "As defined in {{bibref|RFC2616|Section 3.5}}";
          }
          enum "Deflate" {
            description
            "As defined in {{bibref|RFC2616|Section 3.5}}";
          }
        }
      }
      leaf HTTPCompression {
        config true;
        description
        "The value of this parameter represents the HTTP
        Compression mechanism to be used by the CPE when
        communicating with the ACS.";
        type string;
        default "Disabled";
        must ". = ../HTTPCompressionSupported";
      }
      leaf-list LightweightNotificationProtocolsSupported {
        config false;
        description
        "Vendors can extend the enumerated values with vendor
        specific extensions, in which case the rules outlined
        in {{bibref|TR-106a7|Section 3.3}} MUST be adhered to.";
        type enumeration {
          enum "UDP" {
            description
            "As defined in {{bibref|TR-069a5|Annex M}}";
          }
        }
      }
      leaf-list LightweightNotificationProtocolsUsed {
        config true;
        description
        "{{empty}} means that Lightweight Notifications are
        disabled, despite any SetParameterAttributes that have
        been configured on various parameters.";
        type string;
        must ". = ../LightweightNotificationProtocolsSupported";
      }
      leaf LightweightNotificationTriggerInterval {
        config true;
        description
        "A value of 0 means that the trigger interval is
        effectively disabled.  In this case pending Passive
        Lightweight Notifications are only sent when triggered
        by an Active Lightweight Notification.";
        type uint32 {
          range "0..max";
        }
      }
      leaf LightweightNotificationTriggerTime {
        config true;
        description
        "For example, if
        {{param|LightweightNotificationTriggerInterval}} is
        86400 (a day) and if {{param}} is set to UTC midnight
        on some day (in the past, present, or future) then
        Lightweight Notifications for pending Passive
        Lightweight Notifications will occur every day at UTC
        midnight.  These MUST begin on the very next midnight,
        even if {{param}} refers to a day in the future.  The
        Unknown Time value defined in {{bibref|TR-106a2|section
        3.2}} indicates that no particular time reference is
        specified.  That is, the CPE MAY locally choose the
        time reference, and needs only to adhere to the
        specified
        {{param|LightweightNotificationTriggerInterval}}. If
        absolute time is not available to the CPE, its
        Lightweight Notifications behavior MUST be the same as
        if the {{param}} parameter was set to the Unknown Time
        value.";
        type yang:date-and-time;
      }
      leaf UDPLightweightNotificationHost {
        config true;
        description
        "If {{param}} is not implemented or is {{empty}}, and
        UDP Lightweight Notifications are supported, the
        destination host MUST be the same as the ACS (as
        contained in the host portion of the {{param|URL}}).";
        type string {
          length "0..256";
        }
      }
      leaf UDPLightweightNotificationPort {
        config true;
        description
        "If {{param}} is not implemented and UDP Lightweight
        Notifications are supported, the destination port MUST
        be 7547.";
        type uint32;
      }
      leaf InstanceWildcardsSupported {
        config false;
        description
        "A {{true}} value indicates that the CPE supports
        instance wildcards for GPV, GPN and GPA RPC calls, as
        defined in [TR-069a6].";
        type boolean;
      }
      leaf InformParameterNumberOfEntries {
        config false;
        description
        "{{numentries}}";
        type uint32;
      }
      list ManageableDevice {
        key "ManufacturerOUI SerialNumber ProductClass";
        unique "Alias";
        config true;
        description
        "Each entry in this table corresponds to a distinct LAN
        Device that supports Device-Gateway Association
        according to {{bibref|TR-069a2|Annex F}} as indicated
        by the presence of the DHCP option specified in that
        Annex.";
        leaf Alias {
          config true;
          description
          "This parameter is DEPRECATED because {{object}} is a
          transient object.";
          type string {
            length "0..64";
          }
        }
        leaf ManufacturerOUI {
          config true;
          description
          "The value MUST be a valid  OUI as defined in
          {{bibref|OUI}}.";
          type string {
            length "6";
            pattern "[0-9A-F]{6}";
          }
        }
        leaf SerialNumber {
          config true;
          description
          "Serial number of the Device as provided to the
          Gateway by the Device.";
          type string {
            length "0..64";
          }
        }
        leaf ProductClass {
          config true;
          description
          "If the Device does not provide a Product Class, then
          this parameter MUST be {{empty}}.";
          type string {
            length "0..64";
          }
        }
        leaf-list Host {
          config false;
          description
          "For example:
          ''Device.Hosts.Host.1,Device.Hosts.Host.5''";
          type string;
        }
      }
      container AutonomousTransferCompletePolicy {
        description
        "The CPE policy determines the conditions under which
        the CPE notifies the ACS of the completion of file
        transfers that were not specifically requested by the
        ACS.";
        leaf Enable {
          config true;
          description
          "Enable/disable CPE notification of AUTONOMOUS
          TRANSFER COMPLETE events to the ACS.";
          type boolean;
        }
        leaf TransferTypeFilter {
          config true;
          description
          "Note that this includes any backup or restore
          operations that were not specifically requested by
          the ACS.  A backup is regarded as an Upload and a
          restore is regarded as a Download.";
          type enumeration {
            enum "Upload";
            enum "Download";
            enum "Both" {
              description
              "Upload and Download";
            }
          }
        }
        leaf ResultTypeFilter {
          config true;
          description
          "Note that this includes any backup or restore
          operations that were not specifically requested by
          the ACS.  A backup is regarded as an Upload and a
          restore is regarded as a Download.";
          type enumeration {
            enum "Success" {
              description
              "The autonomous file transfer completed
              successfully; i.e., the FaultCode was zero";
            }
            enum "Failure" {
              description
              "The autonomous file transfer did not complete
              successfully; i.e., the FaultCode was non-zero";
            }
            enum "Both" {
              description
              "Success and Failure";
            }
          }
        }
        leaf-list FileTypeFilter {
          config true;
          description
          "Note that {{empty}} indicates that all file types are
          excluded from this filter, effectively disabling CPE
          notification of AUTONOMOUS TRANSFER COMPLETE events
          to the ACS.";
          type string {
            pattern "1 Firmware Upgrade Image|2 Web Content|3 Vendor Configuration File|4 Vendor Log File|X [0-9A-F]{6} .*";
          }
        }
      }
      container DownloadAvailability {
        description
        "This object contains multicast announcement and query
        parameters used for the purpose of downloading files.";
        container Announcement {
          description
          "This object contains multicast announcement
          parameters used to download files.";
          leaf Enable {
            config true;
            description
            "Enable/disable CPE ability to receive and use
            multicast announcements from a server for the
            purpose of downloading files.";
            type boolean;
          }
          leaf Status {
            config false;
            description
            "The status of the announcement service.";
            type enumeration {
              enum "Disabled";
              enum "Enabled";
              enum "Error" {
                description
                "MAY be used by the CPE to indicate a locally
                defined error condition.";
              }
            }
          }
          leaf GroupNumberOfEntries {
            config false;
            description
            "{{numentries}}";
            type uint32;
          }
          list Group {
            key "URL";
            unique "Alias";
            config true;
            description
            "Multicast groups to which the CPE SHOULD listen for
            announcements.";
            leaf Alias {
              config true;
              description
              "{{datatype|expand}}";
              type Alias;
            }
            leaf Enable {
              config true;
              description
              "Enable/disable listening to this multicast group.";
              type boolean;
              default "false";
            }
            leaf Status {
              config false;
              description
              "The status of this group table entry.";
              type enumeration {
                enum "Disabled";
                enum "Enabled";
                enum "Error" {
                  description
                  "MAY be used by the CPE to indicate a locally
                  defined error condition, e.g.  unable to
                  parse received announcements.";
                }
              }
              default "Disabled";
            }
            leaf URL {
              config true;
              description
              "Refer to {{bibref|DVB-TS.102.824}} for an example
              of a URL format that identifies a SAP
              {{bibref|RFC2974}} stream that indicates how to
              use either FLUTE {{bibref|RFC3926}} or DSM-CC
              {{bibref|ISO-13818-6:1998}} to perform the
              download.";
              type string {
                length "0..256";
              }
            }
          }
        }
        container Query {
          description
          "This object contains multicast query parameters used
          to download files.";
          leaf Enable {
            config true;
            description
            "Enable/disable CPE ability to autonomously query a
            server for the purpose of downloading files.";
            type boolean;
          }
          leaf Status {
            config false;
            description
            "The status of the query service.";
            type enumeration {
              enum "Disabled";
              enum "Enabled";
              enum "Error" {
                description
                "MAY be used by the CPE to indicate a locally
                defined error condition, e.g.  unable to
                contact query response server.";
              }
            }
          }
          leaf URL {
            config true;
            description
            "Refer to {{bibref|DVB-TS.102.824}} for an example
            of a URL format that identifies a SOAP interface
            running over HTTP or HTTPS.";
            type string {
              length "0..256";
            }
          }
        }
      }
      container DUStateChangeComplPolicy {
        description
        "The CPE policy determines the conditions under which
        the CPE notifies the ACS of the completion of
        Deployment Unit state changes that were not
        specifically requested via CWMP.";
        leaf Enable {
          config true;
          description
          "Enables/Disables CPE notification of \"12 AUTONOMOUS
          DU STATE CHANGE COMPLETE\" events to the ACS.";
          type boolean;
        }
        leaf-list OperationTypeFilter {
          config true;
          description
          "Operation types not indicated by this list MUST NOT
          be included when the CPE notifies the ACS.  {{empty}}
          is essentially the same as setting {{param|Enable}}
          to {{false}}.";
          type enumeration {
            enum "Install";
            enum "Update";
            enum "Uninstall";
          }
        }
        leaf ResultTypeFilter {
          config true;
          description
          "Indicates the Deployment Unit state change results
          that MUST be included when the CPE notifies the ACS
          of \"12 AUTONOMOUS DU STATE CHANGE COMPLETE\" events.
          State change results omitted from this filter MUST
          NOT be included when the CPE notifies the ACS.";
          type enumeration {
            enum "Success" {
              description
              "The autonomous state change completed
              successfully; i.e., the FaultCode was zero";
            }
            enum "Failure" {
              description
              "The autonomous state change did not complete
              successfully; i.e., the FaultCode was non-zero";
            }
            enum "Both" {
              description
              "All result types independent of Success or
              Failure";
            }
          }
        }
        leaf-list FaultCodeFilter {
          config true;
          description
          "This filter has no effect on the notification of a
          successful autonomous state change.  This filter only
          applies when {{param|ResultTypeFilter}} is set to
          either {{enum|Failure|ResultTypeFilter}} or
          {{enum|Both|ResultTypeFilter}}.  {{empty}} means that
          failed autonomous state changes will not be sent to
          the ACS.";
          type enumeration {
            enum "9001";
            enum "9003";
            enum "9012";
            enum "9013";
            enum "9015";
            enum "9016";
            enum "9017";
            enum "9018";
            enum "9022";
            enum "9023";
            enum "9024";
            enum "9025";
            enum "9026";
            enum "9027";
            enum "9028";
            enum "9029";
            enum "9030";
            enum "9031";
            enum "9032";
          }
        }
      }
      list EmbeddedDevice {
        key "ControllerID ProxiedDeviceID";
        config false;
        description
        "Each entry in this table represents a distinct Proxied
        Device that utilizes the Embedded Object Mechanism
        {{bibref|TR-069a4|Annex J.1.2}} for proxying devices.";
        leaf ControllerID {
          config false;
          description
          "* Doesn't need a {{param}} to ensure its
          {{param|ProxiedDeviceID}} is unique throughout the
          LAN.";
          type string {
            length "0..256";
          }
        }
        leaf ProxiedDeviceID {
          config false;
          description
          "This is an opaque string that is unique to the
          Proxied Device within a specific sub-network within
          the LAN (identified by the {{param|ControllerID}}).
          If the {{param|ControllerID}} is {{empty}} this
          {{param}} is unique across the LAN.";
          type string {
            length "0..256";
          }
        }
        leaf Reference {
          config false;
          description
          "{{noreference}}The value MUST be the path name of a
          table row.  If the referenced object is deleted, this
          {{object}} instance MUST also be removed.  Represents
          the instance of a multi-instanced object that is
          directly controlled by, and has come into existence
          because of, this Proxied Device  that utilizes the
          Embedded Object Mechanism {{bibref|TR-069a4|Annex
          J.1.2}}.";
          type string;
        }
        leaf-list SupportedDataModel {
          config false;
          description
          "Represents the CWMP-DT schema instance(s) that this
          Proxied Device is utilizing.  The CWMP-DT schema
          instance is also the one being utilized by the object
          referenced within {{param|Reference}}.";
          type string;
        }
        leaf-list Host {
          config false;
          description
          "References the {{object|.Hosts.Host}} table entry(s),
          whether active or inactive, that corresponds to this
          proxied LAN device.";
          type string;
        }
        leaf ProxyProtocol {
          config false;
          description
          "Vendors can extend the enumerated values with vendor
          specific extensions, in which case the rules outlined
          in {{bibref|TR-106a6|3.3}} MUST be adhered to.";
          type enumeration {
            enum "Z-Wave" {
              description
              "see {{bibref|Z-Wave}}";
            }
            enum "ZigBee" {
              description
              "see {{bibref|ZigBee}}";
            }
            enum "UPnP-DM" {
              description
              "see {{bibref|UPnP-DM:1}}";
            }
            enum "ETSI-M2M" {
              description
              "see {{bibref|ETSIM2MFA}}";
            }
          }
        }
        leaf ProxyProtocolReference {
          config false;
          description
          "{{reference|a protocol object that uses the
          {{param|ProxyProtocol}}}}";
          type string;
        }
        leaf-list DiscoveryProtocol {
          config false;
          description
          "Vendors can extend the enumerated values with vendor
          specific extensions, in which case the rules outlined
          in {{bibref|TR-106a3|Section 3.3}} MUST be adhered
          to.";
          type enumeration {
            enum "Z-Wave" {
              description
              "see {{bibref|Z-Wave}}";
            }
            enum "ZigBee" {
              description
              "see {{bibref|ZigBee}}";
            }
            enum "UPnP" {
              description
              "see {{bibref|UPnP-DAv1}}";
            }
            enum "ETSI-M2M" {
              description
              "see {{bibref|ETSIM2MFA}}";
            }
          }
        }
        leaf-list DiscoveryProtocolReference {
          config false;
          description
          "For objects discovered by the ETSI-M2M discovery
          protocol, the {{param}} would contain items that are
          references to instances of
          ETSIM2M.SCL.{i}.AreaNwkDeviceInfoInstance.";
          type string;
        }
        leaf CommandProcessed {
          config false;
          description
          "Whether or not the CPE Proxier has successfully
          communicated all pending configuration commands down
          to the Proxied Device.";
          type enumeration {
            enum "Pending";
            enum "Retrying";
            enum "Success";
            enum "Error";
          }
        }
        leaf CommandProcessingErrMsg {
          config false;
          description
          "Detailed {{param|CommandProcessed}} error description
          (vendor specific).";
          type string {
            length "0..1024";
          }
        }
        leaf LastSyncTime {
          config false;
          description
          "The Unknown Time value, as defined in
          {{bibref|TR-106a6}}, indicates that the Proxied
          Device's state has not been synchronized since the
          CPE Proxier was last rebooted.";
          type yang:date-and-time;
        }
      }
      list VirtualDevice {
        key "ManufacturerOUI ProductClass SerialNumber";
        config false;
        description
        "Each entry in this table represents a distinct Proxied
        Device that utilizes the Virtual CWMP Device Mechanism
        {{bibref|TR-069a4|Annex I.1.1}} for proxying devices.";
        leaf ManufacturerOUI {
          config false;
          description
          "The value MUST be a valid OUI as defined in
          {{bibref|OUI}}.";
          type string {
            length "6";
            pattern "[0-9A-F]{6}";
          }
        }
        leaf ProductClass {
          config false;
          description
          "Identifier of the class of product of the associated
          Proxied Device for which the serial number applies.";
          type string {
            length "0..64";
          }
        }
        leaf SerialNumber {
          config false;
          description
          "Serial number of the associated Proxied Device.";
          type string {
            length "0..64";
          }
        }
        leaf-list Host {
          config false;
          description
          "{{list}} {{reference}}  References all the
          {{object|.Hosts.Host}} table entries, whether active
          or inactive, that correspond to this proxied LAN
          device.  There can be multiple such entries if the
          Proxied Device has more than one network interface.";
          type string;
        }
        leaf ProxyProtocol {
          config false;
          description
          "Vendors can extend the enumerated values with vendor
          specific extensions, in which case the rules outlined
          in {{bibref|TR-106a6|3.3}} MUST be adhered to.";
          type enumeration {
            enum "Z-Wave" {
              description
              "see {{bibref|Z-Wave}}";
            }
            enum "ZigBee" {
              description
              "see {{bibref|ZigBee}}";
            }
            enum "UPnP-DM" {
              description
              "see {{bibref|UPnP-DM:1}}";
            }
            enum "ETSI-M2M" {
              description
              "see {{bibref|ETSIM2MFA}}";
            }
          }
        }
        leaf ProxyProtocolReference {
          config false;
          description
          "{{reference|a protocol object that uses the
          {{param|ProxyProtocol}}}}";
          type string;
        }
        leaf-list DiscoveryProtocol {
          config false;
          description
          "Vendors can extend the enumerated values with vendor
          specific extensions, in which case the rules outlined
          in {{bibref|TR-106a3|Section 3.3}} MUST be adhered
          to.";
          type enumeration {
            enum "Z-Wave" {
              description
              "see {{bibref|Z-Wave}}";
            }
            enum "ZigBee" {
              description
              "see {{bibref|ZigBee}}";
            }
            enum "UPnP" {
              description
              "see {{bibref|UPnP-DAv1}}";
            }
            enum "ETSI-M2M" {
              description
              "see {{bibref|ETSIM2MFA}}";
            }
          }
        }
        leaf-list DiscoveryProtocolReference {
          config false;
          description
          "For objects discovered by the ETSI-M2M discovery
          protocol, the {{param}} would contain items that are
          references to instances of
          ETSIM2M.SCL.{i}.AreaNwkDeviceInfoInstance.";
          type string;
        }
      }
      container StandbyPolicy {
        description
        "NOTE: \"CR\", as used in the names and descriptions of
        the parameters defined in this object, refers to the
        Connection Request concept defined in TR-069.";
        leaf CRUnawarenessMaxDuration {
          config true;
          description
          "If the value is -1, the CPE MUST NOT ever issue
          WAKEUP Events for having been non CR-aware.";
          type int32 {
            range "-1..max";
          }
          default "-1";
        }
        leaf MaxMissedPeriodic {
          config true;
          description
          "If the value is -1, the CPE MUST NOT ever issue
          WAKEUP Events for exceeding that limit.";
          type int32 {
            range "-1..max";
          }
          default "-1";
        }
        leaf NotifyMissedScheduled {
          config true;
          description
          "When waking up from a non fully Timer-Aware Standby
          that made it miss at least one Scheduled Contact, the
          CPE MUST issue a WAKEUP Event if this parameter is
          {{true}}.";
          type boolean;
          default "false";
        }
        leaf NetworkAwarenessCapable {
          config false;
          description
          "Indicates that the CPE is capable of CR-Aware
          Standby.";
          type boolean;
        }
        leaf SelfTimerCapable {
          config false;
          description
          "Indicates that the CPE is capable of Timer-Aware
          Standby.";
          type boolean;
        }
        leaf CRAwarenessRequested {
          config true;
          description
          "If {{param|NetworkAwarenessCapable}} and this
          parameter are both {{true}}, the CPE MUST NOT go into
          a non CR-Aware Standby state.";
          type boolean;
          default "false";
        }
        leaf PeriodicAwarenessRequested {
          config true;
          description
          "If {{param|SelfTimerCapable}} and this parameter are
          both {{true}}, the CPE MUST NOT go into a standby
          state that prevents it from honoring Periodic
          Contacts.";
          type boolean;
          default "false";
        }
        leaf ScheduledAwarenessRequested {
          config true;
          description
          "*if {{param|SelfTimerCapable}} is {{false}}, the CPE
          MUST NOT go into Standby before the Scheduled Contact
          has been honored.";
          type boolean;
        }
      }
      list InformParameter {
        key "ParameterName";
        unique "Alias";
        config true;
        description
        "This table does not include Forced Inform Parameters,
        and Forced Inform Parameters are not allowed to be
        inserted into this table.  Any attempt by an ACS to
        configure this table to contain a Forced Inform
        Parameter MUST result in the failure of the
        SetParameterValues RPC with error code 9007.";
        leaf Enable {
          config true;
          description
          "Enables or disables this {{object}}.";
          type boolean;
          default "false";
        }
        leaf Alias {
          config true;
          description
          "{{datatype|expand}}";
          type Alias;
        }
        leaf ParameterName {
          config true;
          description
          "If the pattern does not match any existing Parameters
          at the time that the CPE is creating the Inform RPC,
          then this {{object|#.InformParameter}} instance is
          not included in the Inform’s ParameterList argument.";
          type string {
            length "0..256";
          }
        }
        leaf-list EventList {
          config true;
          description
          "{{empty}} means all events except \"4 VALUE CHANGE\".";
          type string;
        }
      }
      container HeartbeatPolicy {
        description
        "If this object is supported then the CPE MUST support
        the requirements of {{bibref|TR-069|Annex O}}.";
        leaf Enable {
          config true;
          description
          "When {{true}}, Heartbeat events are enabled to be
          sent to the ACS based on the values of the
          {{param|ReportingInterval}} and
          {{param|InitiationTime}} parameters.";
          type boolean;
        }
        leaf ReportingInterval {
          config true;
          description
          "The duration in {{units}} of the interval for which
          the CPE MUST attempt to connect with the ACS and call
          the Inform method if {{param|Enable}} is {{true}}.";
          type uint32 {
            range "30..max";
          }
        }
        leaf InitiationTime {
          config true;
          description
          "If absolute time is not available to the CPE, its
          Heartbeat Inform behavior MUST be the same as if the
          {{param}} parameter was set to the Unknown Time
          value.";
          type yang:date-and-time;
        }
      }
    }
    container SoftwareModules {
      description
      "Top level object for dynamically managed software
      applications.";
      leaf ExecEnvNumberOfEntries {
        config false;
        description
        "{{numentries}}";
        type uint32;
      }
      leaf DeploymentUnitNumberOfEntries {
        config false;
        description
        "{{numentries}}";
        type uint32;
      }
      leaf ExecutionUnitNumberOfEntries {
        config false;
        description
        "{{numentries}}";
        type uint32;
      }
      list ExecEnv {
        key "Name";
        unique "Alias";
        config true;
        description
        "The Execution Environments that are available on the
        device, along with their properties and configurable
        settings.";
        leaf Enable {
          config true;
          description
          "Disabling an Execution Environment could place the
          device in a non-manageable state.  For example, if
          the operating system itself was modeled as an
          {{object}} and the ACS disabled it, the CWMP
          management agent might be terminated leaving the
          device unmanageable.";
          type boolean;
        }
        leaf Status {
          config false;
          description
          "Indicates the status of this {{object}}.";
          type enumeration {
            enum "Up";
            enum "Error";
            enum "Disabled";
          }
        }
        leaf Reset {
          config true;
          description
          "# The Execution Environment MUST be restarted after
          all other restoration requirements have been met";
          type boolean;
        }
        leaf Alias {
          config true;
          description
          "{{datatype|expand}}";
          type Alias;
        }
        leaf Name {
          config true;
          description
          "A Name provided by the CPE that adequately
          distinguishes this {{object}} from all other
          {{object}} instances.";
          type string {
            length "0..32";
          }
        }
        leaf Type {
          config false;
          description
          "Indicates the complete type and specification version
          of this {{object}}.";
          type string {
            length "0..64";
          }
        }
        leaf InitialRunLevel {
          config true;
          description
          "If the value of {{param|CurrentRunLevel}} is -1, then
          the value of this parameter is irrelevant when read
          and setting its value has no impact on the Run Level
          of this {{object}}.";
          type uint32 {
            range "min..65535";
          }
        }
        leaf RequestedRunLevel {
          config true;
          description
          "Setting this value when {{param|CurrentRunLevel}} is
          -1 has no impact to the Run Level of this {{object}}.";
          type int32 {
            range "-1..65535";
          }
        }
        leaf CurrentRunLevel {
          config false;
          description
          "If {{param}} is -1 then Run Levels are not supported
          by this {{object}} and setting
          {{param|InitialRunLevel}} or
          {{param|RequestedRunLevel}} will not impact the Run
          Level of this {{object}}.";
          type int32 {
            range "-1..65535";
          }
        }
        leaf InitialExecutionUnitRunLevel {
          config true;
          description
          "If the value of {{param|CurrentRunLevel}} is -1, then
          the value of this parameter is irrelevant when read
          and setting its value has no impact on the Run Level
          of any Execution Unit.";
          type int32 {
            range "-1..65535";
          }
        }
        leaf Vendor {
          config false;
          description
          "The vendor that produced this {{object}}.";
          type string {
            length "0..128";
          }
        }
        leaf Version {
          config false;
          description
          "The Version of this {{object}} as specified by the
          Vendor that implemented this {{object}}, not the
          version of the specification.";
          type string {
            length "0..32";
          }
        }
        leaf ParentExecEnv {
          config false;
          description
          "If this value is {{empty}} then this is the Primary
          Execution Environment.";
          type string;
        }
        leaf AllocatedDiskSpace {
          config false;
          description
          "The amount of disk space measured in {{units}}
          allocated to this {{object}}.  A value of -1 MUST be
          used for {{object}} instances where this parameter is
          not applicable.";
          type int32 {
            range "-1..max";
          }
        }
        leaf AvailableDiskSpace {
          config false;
          description
          "The amount of disk space measured in {{units}}
          currently available to this {{object}}.  This value
          changes as the {{object|#.ExecutionUnit}} instances
          associated with this {{object}} consumes disk space.
          A value of -1 MUST be used for {{object}} instances
          where this parameter is not applicable.";
          type int32 {
            range "-1..max";
          }
        }
        leaf AllocatedMemory {
          config false;
          description
          "The amount of physical RAM measured in {{units}}
          allocated to this {{object}}.  A value of -1 MUST be
          used for {{object}} instances where this parameter is
          not applicable.";
          type int32 {
            range "-1..max";
          }
        }
        leaf AvailableMemory {
          config false;
          description
          "The amount of physical RAM measured in {{units}}
          currently available to this {{object}}.  This value
          changes as the {{object|#.ExecutionUnit}} instances
          associated with this {{object}} are started/stopped
          and consume the physical RAM.  A value of -1 MUST be
          used for {{object}} instances where this parameter is
          not applicable.";
          type int32 {
            range "-1..max";
          }
        }
        leaf-list ActiveExecutionUnits {
          config false;
          description
          "Represents the {{object|#.ExecutionUnit}} instances
          currently running on this {{object}}.  This parameter
          only contains {{object|#.ExecutionUnit}} instances
          that currently have a
          {{param|#.ExecutionUnit.{i}.Status}} of
          {{enum|Active|#.ExecutionUnit.{i}.Status}}.";
          type string;
        }
        leaf-list ProcessorRefList {
          config false;
          description
          "Represents the processors that this {{object}} has
          available to it.";
          type string;
        }
      }
      list DeploymentUnit {
        key "UUID Version ExecutionEnvRef";
        unique "Alias";
        config true;
        description
        "A new instance of this table gets created during the
        installation of a Software Module.";
        leaf UUID {
          config true;
          description
          "This value MUST NOT be altered when the {{object}} is
          updated.";
          type string {
            length "0..36";
          }
        }
        leaf DUID {
          config false;
          description
          "Deployment Unit Identifier chosen by the targeted
          {{object|#.ExecEnv}}.  The format of this value is
          Execution Environment specific.";
          type string {
            length "0..64";
          }
        }
        leaf Alias {
          config true;
          description
          "{{datatype|expand}}";
          type Alias;
        }
        leaf Name {
          config false;
          description
          "The value of this parameter is used in the generation
          of the {{param|UUID}} based on the rules defined in
          {{bibref|TR-069a3|Annex H}}.";
          type string {
            length "0..64";
          }
        }
        leaf Status {
          config false;
          description
          "Indicates the status of this {{object}}.";
          type enumeration {
            enum "Installing" {
              description
              "This instance is in the process of being
              Installed and SHOULD transition to the
              {{enum|Installed}} state.";
            }
            enum "Installed" {
              description
              "This instance has been successfully Installed.
              The {{param|Resolved}} flag SHOULD also be
              referenced for dependency resolution.";
            }
            enum "Updating" {
              description
              "This instance is in the process of being Updated
              and SHOULD transition to the {{enum|Installed}}
              state.";
            }
            enum "Uninstalling" {
              description
              "This instance is in the process of being
              Uninstalled and SHOULD transition to the
              {{enum|Uninstalled}} state.";
            }
            enum "Uninstalled" {
              description
              "This instance has been successfully Uninstalled.
              This status will typically not be seen within a
              {{object}} instance.";
            }
          }
        }
        leaf Resolved {
          config false;
          description
          "Indicates whether or not this {{object}} has resolved
          all of its dependencies.";
          type boolean;
        }
        leaf URL {
          config false;
          description
          "Contains the URL used by the most recent
          ChangeDUState RPC to either Install or Update this
          {{object}}.";
          type string {
            length "0..1024";
          }
        }
        leaf Description {
          config false;
          description
          "Textual description of this {{object}}. The format of
          this value is Execution Environment specific.";
          type string {
            length "0..256";
          }
        }
        leaf Vendor {
          config false;
          description
          "The value of this parameter is used in the generation
          of the {{param|UUID}} based on the rules defined in
          {{bibref|TR-069a3|Annex H}}.";
          type string {
            length "0..128";
          }
        }
        leaf Version {
          config true;
          description
          "Version of this {{object}}.  The format of this value
          is Execution Environment specific.";
          type string {
            length "0..32";
          }
        }
        leaf-list VendorLogList {
          config false;
          description
          "Not all {{object}} instances will actually have a
          corresponding vendor log file, in which case the
          value of this parameter will be {{empty}}.";
          type string;
        }
        leaf-list VendorConfigList {
          config false;
          description
          "Not all {{object}} instances will actually have a
          corresponding vendor config file, in which case the
          value of this parameter will be {{empty}}.";
          type string;
        }
        leaf-list ExecutionUnitList {
          config false;
          description
          "Represents the {{object|#.ExecutionUnit}} instances
          that are associated with this {{object}} instance.";
          type string;
        }
        leaf ExecutionEnvRef {
          config true;
          description
          "Represents the {{object|#.ExecEnv}} instance where
          this {{object}} instance is installed.";
          type string;
        }
      }
      list ExecutionUnit {
        key "EUID";
        unique "Alias";
        config true;
        description
        "Each {{object}} MAY also contain a set of vendor
        specific parameters displaying status and maintaining
        configuration that reside under the
        {{object|Extensions}} object.";
        leaf EUID {
          config true;
          description
          "The format of this value is Execution Environment
          specific, but it MUST be unique across
          {{object|#.ExecEnv}} instances.  Thus, it is
          recommended that this be a combination of the
          {{param|#.ExecEnv.{i}.Name}} and an Execution
          Environment local unique value.";
          type string {
            length "0..64";
          }
        }
        leaf Alias {
          config true;
          description
          "{{datatype|expand}}";
          type Alias;
        }
        leaf Name {
          config false;
          description
          "The name of this {{object}} as it pertains to its
          associated {{object|#.DeploymentUnit}}, which SHOULD
          be unique across all {{object}} instances contained
          within its associated {{object|#.DeploymentUnit}}.";
          type string {
            length "0..32";
          }
        }
        leaf ExecEnvLabel {
          config false;
          description
          "The name of this {{object}} as provided by the
          {{object|#.ExecEnv}}, which SHOULD be unique across
          all {{object}} instances contained within a specific
          {{object|#.ExecEnv}}.";
          type string {
            length "0..64";
          }
        }
        leaf Status {
          config false;
          description
          "Indicates the status of this {{object}}.";
          type enumeration {
            enum "Idle" {
              description
              "This instance is in an Idle state and not
              running.";
            }
            enum "Starting" {
              description
              "This instance is in the process of Starting and
              SHOULD transition to the {{enum|Active}} state.";
            }
            enum "Active" {
              description
              "This instance is currently running.";
            }
            enum "Stopping" {
              description
              "This instance is in the process of Stopping and
              SHOULD transition to the {{enum|Idle}} state.";
            }
          }
        }
        leaf RequestedState {
          config true;
          description
          "If this {{object}} is associated with an Execution
          Environment that is disabled and an attempt is made
          to alter this value, then a CWMP Fault MUST be
          generated.";
          type enumeration {
            enum "Idle" {
              description
              "If this {{object}} is currently in
              {{enum|Starting|Status}} or
              {{enum|Active|Status}} the CPE will attempt to
              Stop the Execution Unit; otherwise this requested
              state is ignored.";
            }
            enum "Active" {
              description
              "If this {{object}} is currently in
              {{enum|Idle|Status}} the CPE will attempt to
              Start the Execution Unit.  If this {{object}} is
              in {{enum|Stopping|Status}} the request is
              rejected and a fault raised.  Otherwise this
              requested state is ignored.";
            }
          }
        }
        leaf ExecutionFaultCode {
          config false;
          description
          "For fault codes not included in this list, the vendor
          MAY include vendor-specific values, which MUST use
          the format defined in {{bibref|TR-106a4|Section
          3.3}}.";
          type enumeration {
            enum "NoFault";
            enum "FailureOnStart";
            enum "FailureOnAutoStart";
            enum "FailureOnStop";
            enum "FailureWhileActive";
            enum "DependencyFailure";
            enum "UnStartable";
          }
        }
        leaf ExecutionFaultMessage {
          config false;
          description
          "If {{param|ExecutionFaultCode}} has the value of
          {{enum|NoFault|ExecutionFaultCode}} then the value of
          this parameter MUST {{empty}} and ignored by the ACS.";
          type string {
            length "0..256";
          }
        }
        leaf AutoStart {
          config true;
          description
          "If {{false}} this {{object}} will not be started
          after its {{object|#.ExecEnv}} is either rebooted or
          restarted until it is explicitly commanded to do so
          by either the ACS or another Execution Unit.";
          type boolean;
        }
        leaf RunLevel {
          config true;
          description
          "If the value of
          {{param|#.ExecEnv.{i}.CurrentRunLevel}} is -1, then
          the associated {{object|#.ExecEnv.}} doesn't support
          Run Levels, thus the value of this parameter is
          irrelevant when read and setting its value has no
          impact to the Run Level of this {{object}}.";
          type uint32 {
            range "min..65535";
          }
        }
        leaf Vendor {
          config false;
          description
          "Vendor of this {{object}}.";
          type string {
            length "0..128";
          }
        }
        leaf Version {
          config false;
          description
          "Version of the {{object}}.  The format of this value
          is Execution Environment specific.";
          type string {
            length "0..32";
          }
        }
        leaf Description {
          config false;
          description
          "Textual description of this {{object}}. The format of
          this value is Execution Environment specific.";
          type string {
            length "0..256";
          }
        }
        leaf DiskSpaceInUse {
          config false;
          description
          "The amount of disk space measured in {{units}}
          currently being used by this {{object}}.  A value of
          -1 MUST be used for {{object}} instances where this
          parameter is not applicable.";
          type int32 {
            range "-1..max";
          }
        }
        leaf MemoryInUse {
          config false;
          description
          "The amount of physical RAM measured in {{units}}
          currently being used by this {{object}}.  A value of
          -1 MUST be used for {{object}} instances where this
          parameter is not applicable.";
          type int32 {
            range "-1..max";
          }
        }
        leaf-list References {
          config false;
          description
          "NOTE: All other objects and parameters (i.e.  not
          multi-instanced objects) that this {{object}} has
          caused to come into existence can be discovered via
          the {{object|.DeviceInfo.SupportedDataModel.{i}.}}
          table.";
          type string;
        }
        leaf-list AssociatedProcessList {
          config false;
          description
          "If {{param|Status}} is not {{enum|Active|Status}} it
          is expected that this list will be {{empty}}.  Some
          {{object}} instances MIGHT NOT have any system
          processes irrespective of the value of
          {{param|Status}}.";
          type string;
        }
        leaf-list VendorLogList {
          config false;
          description
          "Not all {{object}} instances will actually have a
          corresponding vendor log file, in which case the
          value of this parameter will be {{empty}}.";
          type string;
        }
        leaf-list VendorConfigList {
          config false;
          description
          "Not all {{object}} instances will actually have a
          corresponding vendor config file, in which case the
          value of this parameter will be {{empty}}.";
          type string;
        }
        leaf-list SupportedDataModelList {
          config false;
          description
          "Represents the CWMP-DT schema instances that have
          been introduced to this device because of the
          existence of this {{object}}.";
          type string;
        }
        leaf ExecutionEnvRef {
          config false;
          description
          "Represents the {{object|#.ExecEnv}} that this
          {{object}} is associated with.";
          type string;
        }
        container Extensions {
          description
          "See {{bibref|TR-157a3|Appendix II.3.2}} for more
          description and some examples.";
        }
      }
    }
    container ETSIM2M {
      description
      "The {{object}} object represents the management object
      for the Remote Entity Functions (REM) functions defined
      in the M2M Functional Architecture {{bibref|ETSIM2MFA}}.";
      leaf SCLNumberOfEntries {
        config false;
        description
        "{{numentries}}";
        type uint32;
      }
      list SCL {
        key "Alias";
        config true;
        description
        "{{keys}}";
        leaf Enable {
          config true;
          description
          "Administratively enables or disables this instance.";
          type boolean;
          default "false";
        }
        leaf Alias {
          config true;
          description
          "{{datatype|expand}}";
          type Alias;
        }
        leaf-list AnnouncedToSCLList {
          config true;
          description
          "Section 9.3.2.28 of the M2M Functional Architecture
          {{bibref|ETSIM2MFA}} and Section 10.3.2.7 of the M2M
          mIa, dIa and mId Interfaces
          {{bibref|ETSIM2MInterfaces}} describes the process of
          announcing and deannouncing of resources within a
          SCL.";
          type string;
        }
        leaf SAFPolicySetNumberOfEntries {
          config false;
          description
          "{{numentries}}";
          type uint32;
        }
        leaf AreaNwkInstanceNumberOfEntries {
          config false;
          description
          "{{numentries}}";
          type uint32;
        }
        leaf AreaNwkDeviceInfoInstanceNumberOfEntries {
          config false;
          description
          "{{numentries}}";
          type uint32;
        }
        container Discovery {
          description
          "Section 9.3.2.27 of the M2M Functional Architecture
          {{bibref|ETSIM2MFA}} describes the process of
          discovery of resources within a SCL.";
          leaf MaxNumberOfDiscovRecords {
            config true;
            description
            "A value of 0 indicates that the SCL does not have a
            limit for this parameter.";
            type uint32;
          }
          leaf MaxSizeOfDiscovAnswer {
            config true;
            description
            "A value of 0 indicates that the SCL does not have a
            limit for this parameter.";
            type uint32;
          }
        }
        container Reregistration {
          description
          "This object represents the properties and status
          necessary for a SCL to reregister with one or more
          NSCLs.";
          leaf-list RegTargetNSCLList {
            config true;
            description
            "When modified the contents of this parameter
            replace the {{param}} received during the bootstrap
            procedure.";
            type string;
          }
          leaf-list RegSearchStrings {
            config true;
            description
            "Sections 9.2.3.6.2 and 9.2.3.6.4 of the M2M
            Functional Architecture {{bibref|ETSIM2MFA}}
            describe the usage for this parameter.";
            type string;
          }
          leaf RegAccessRightID {
            config true;
            description
            "URI {{bibref|RFC3986}} that represents the
            identifier of the access right resource.  The value
            of this parameter is maintained by the NSCL and
            used by the SCL as a default access right
            identifier for re-registration to NSCLs.";
            type string;
          }
          leaf RegExpirationDuration {
            config true;
            description
            "The duration, in {{units}}, that the SCL will use
            in its next re-registration attempt.  Any negative
            value represents an infinite duration.";
            type int32;
            default "-1";
          }
          leaf Reregistration {
            config true;
            description
            "{{command}} When set to {{true}}, triggers an
            immediate re-registration action where the SCL
            re-registers with the SCLs in the
            {{param|RegTargetNSCLList}} .";
            type boolean;
          }
          container ActionStatus {
            description
            "This object represents the status of the
            Reregistration action.";
            leaf Progress {
              config false;
              description
              "The progress, in {{units}}, of the Reregistration
              action.  The progress is measured from 0-100%. A
              value of 0 indicates that the action has not
              started.  A value of 100 indicates that the
              action has completed.";
              type uint32 {
                range "0..100";
              }
            }
            leaf FinalStatus {
              config false;
              description
              "{{enum}}";
              type enumeration {
                enum "SUCCESS";
                enum "FAILURE";
              }
            }
          }
        }
        list SAFPolicySet {
          key "Alias";
          config true;
          description
          "There is exactly one {{object}} instance with a
          {{param|PolicyScope}} value of \"default\".";
          leaf Enable {
            config true;
            description
            "Administratively enables or disables this instance.";
            type boolean;
            default "false";
          }
          leaf Alias {
            config true;
            description
            "{{datatype|expand}}";
            type Alias;
          }
          leaf-list PolicyScope {
            config true;
            description
            "When this parameter is set to {{empty}}, the value
            represents an unknown {{object|#.SAFPolicySet}} and
            the {{object|#.SAFPolicySet}} is not to be used.";
            type string;
          }
          leaf ANPPolicyNumberOfEntries {
            config false;
            description
            "{{numentries}}";
            type uint32;
          }
          list ANPPolicy {
            key "ANName";
            unique "Alias";
            config true;
            description
            "{{keys}}";
            leaf Enable {
              config true;
              description
              "Administratively enables or disables this
              instance.";
              type boolean;
              default "false";
            }
            leaf Alias {
              config true;
              description
              "{{datatype|expand}}";
              type Alias;
            }
            leaf ANName {
              config true;
              description
              "This parameter is the name of the access network
              provider and used to determine for which access
              network the policies defined in the
              {{object|#.ANPPolicy}} table will apply.";
              type string;
            }
            leaf BlockPeriodNumberOfEntries {
              config false;
              description
              "{{numentries}}";
              type uint32;
            }
            leaf RequestCategoryNumberOfEntries {
              config false;
              description
              "{{numentries}}";
              type uint32;
            }
            list BlockPeriod {
              key "FailedAttempts";
              unique "Alias";
              config true;
              description
              "A block period defines how long the device will
              wait before re-trying to establish connectivity
              via the access network after the previous attempt
              has failed.";
              leaf Enable {
                config true;
                description
                "Administratively enables or disables this
                instance.";
                type boolean;
                default "false";
              }
              leaf Alias {
                config true;
                description
                "{{datatype|expand}}";
                type Alias;
              }
              leaf FailedAttempts {
                config true;
                description
                "The SCL will apply the {{object}} entry with
                the largest number of consecutive failed
                attempts that is smaller or equal to the actual
                number of consecutive failed attempts.";
                type uint32;
              }
              leaf BlockDuration {
                config true;
                description
                "The duration, in {{units}}, to which to block
                further access attempts.";
                type int32;
                default "0";
              }
            }
            list RequestCategory {
              key "RCAT";
              unique "Alias";
              config true;
              description
              "This table contains the Request Category (RCAT)
              policy items for defining when it is appropriate
              to use the access network for processing
              requests.";
              leaf Enable {
                config true;
                description
                "Administratively enables or disables this
                instance.";
                type boolean;
                default "false";
              }
              leaf Alias {
                config true;
                description
                "{{datatype|expand}}";
                type Alias;
              }
              leaf RCAT {
                config true;
                description
                "An RCAT is a string that represents a request
                category used for policy enforcement.";
                type string;
              }
              leaf ScheduleNumberOfEntries {
                config false;
                description
                "{{numentries}}";
                type uint32;
              }
            }
          }
          container M2MSPPolicy {
            description
            "This object maintains the SAF handling policies'
            properties that are controlled by the M2M service
            provider for a request.";
            leaf DefaultRCATValue {
              config true;
              description
              "The default RCAT value to use for requests to
              remotely hosted resources during SAF-handling
              when no RCAT value was specified in the request.";
              type string;
            }
            leaf RequestCategoryNumberOfEntries {
              config false;
              description
              "{{numentries}}";
              type uint32;
            }
            list RequestCategory {
              key "RCAT";
              unique "Alias";
              config true;
              description
              "Processing behavior for the use of M2M Service
              Provider policies is defined in section
              10.3.1.2.2.1 of the M2M mIa, dIa and mId
              Interfaces {{bibref|ETSIM2MInterfaces}} document.";
              leaf Enable {
                config true;
                description
                "Administratively enables or disables this
                instance.";
                type boolean;
                default "false";
              }
              leaf Alias {
                config true;
                description
                "{{datatype|expand}}";
                type Alias;
              }
              leaf RCAT {
                config true;
                description
                "An RCAT is a string that represents a request
                category used for policy enforcement.";
                type string;
              }
              leaf TolerableDelay {
                config true;
                description
                "A value of -1 represents an infinite duration.";
                type int32 {
                  range "-1..max";
                }
                default "0";
              }
              leaf Thresh {
                config true;
                description
                "A value of 0 indicates that the request should
                be transmitted immediately.";
                type uint32;
                default "0";
              }
              leaf Mem {
                config true;
                description
                "{{pattern}}";
                type string {
                  pattern "([0-9]{1,15}?[BKMGT])|^$";
                }
              }
              leaf-list RankedANList {
                config true;
                description
                "The list is a prioritized set of Access
                Networks where the preference of using an
                Access Network is based on order of the list
                items with the lowest order list item as the
                most preferred Access Network.";
                type string;
              }
            }
          }
        }
        list AreaNwkInstance {
          key "ID";
          config false;
          description
          "Section 5.3.5 of the M2M Functional Architecture
          {{bibref|ETSIM2MFA}} describes the REM functionality
          expected of a SCL for an M2M Device.";
          leaf ID {
            config false;
            description
            "URI {{bibref|RFC3986}} that represents the
            identifier of the instance.";
            type string;
          }
          leaf AreaNwkType {
            config false;
            description
            "Devices (D' and d) that connect to an SCL are said
            to be \"attached devices\" and are organized by M2M
            Area Networks within the {{object|##.SCL}}
            instance.  The {{param}} is an
            implementation-chosen string that indicates the
            type of M2M Area Network.";
            type string;
          }
          leaf-list ListOfDevices {
            config false;
            description
            "The list represents the M2M Devices (D', d) that
            are attached to this {{object|##.SCL}} instance
            that are within this {{object}} instance.  The list
            does not contain an instance for this CPE.";
            type string;
          }
          leaf PropertyNumberOfEntries {
            config false;
            description
            "{{numentries}}";
            type uint32;
          }
          list Property {
            key "_id";
            leaf "_id" {
              type "uint32";
            }
            config false;
            description
            "At a minimum, a property instance MUST exist that
            defines  an attribute that describes the IP layer
            address type (e.g., IPv4, IPv6, non-IP) of this M2M
            Area Network.";
            leaf Name {
              config false;
              description
              "The name of the property";
              type string;
            }
            leaf Value {
              config false;
              description
              "The value of the property.";
              type string;
            }
          }
        }
        list AreaNwkDeviceInfoInstance {
          key "_id";
          leaf "_id" {
            type "uint32";
          }
          config true;
          description
          "Instances of this table are created and deleted by
          the CPE. The ACS MAY modify the writeable parameters
          of this object instance but  it is possible that the
          value set by the ACS is not retained between reboots
          of the M2M Device.";
          leaf AreaNwkInstance {
            config false;
            description
            "{{reference}}";
            type string;
          }
          leaf-list Host {
            config false;
            description
            "{{list}} {{reference|the {{object|.Hosts.Host}}
            table entry that represents an active or inactive
            M2M Device}}";
            type string;
          }
          leaf-list ListOfDeviceNeighbors {
            config false;
            description
            "{{list}} {{reference}} References all the
            {{object|.Hosts.Host}} table entries, whether
            active or inactive, that represent the reachable
            neighbors of this M2M Device (D' or d).";
            type string;
          }
          leaf-list ListOfDeviceApplications {
            config false;
            description
            "Table B.58 of the M2M Functional Architecture
            {{bibref|ETSIM2MFA}} describes this parameter.";
            type string;
          }
          leaf SleepInterval {
            config true;
            description
            "Note: When this value is modified, the CPE could
            modify the {{param}} for this M2M Device in other
            Area Networks.";
            type uint32;
          }
          leaf SleepDuration {
            config true;
            description
            "Note: When this value is modified, the CPE could
            modify the {{param}} for this M2M Device in other
            Area Networks.";
            type uint32;
          }
          leaf Status {
            config false;
            description
            "{{enum}}";
            type enumeration {
              enum "ASLEEP";
              enum "AWAKE";
            }
          }
          leaf Active {
            config false;
            description
            "The ability to list inactive M2M Devices is
            OPTIONAL.  If the CPE includes inactive M2MDevices
            in this table, {{param}} is set to {{false}}  for
            each inactive M2M Device.  The length of time an
            inactive M2M Device remains listed in this table is
            a local matter to the CPE.";
            type boolean;
          }
          leaf PropertyNumberOfEntries {
            config false;
            description
            "{{numentries}}";
            type uint32;
          }
          list Property {
            key "_id";
            leaf "_id" {
              type "uint32";
            }
            config false;
            description
            "For example, if the
            {{param|##.AreaNwkInstance.{i}.AreaNwkType}} value
            is ZigBee, this
            {{object|##.AreaNwkDeviceInfoInstance}} contains
            ZigBee-specific parameters that are not formally
            modeled for this
            {{object|##.AreaNwkDeviceInfoInstance}} instance.";
            leaf Name {
              config false;
              description
              "The name of the property";
              type string;
            }
            leaf Value {
              config false;
              description
              "The value of the property.";
              type string;
            }
          }
        }
      }
    }
    container GatewayInfo {
      description
      "This object contains information associated with a
      connected Internet Gateway Device.";
      leaf ManufacturerOUI {
        config false;
        description
        "{{empty}} indicates that there is  no associated
        Internet Gateway Device that has been detected.";
        type string {
          length "0..6";
          pattern "^$|[0-9A-F]{6}";
        }
      }
      leaf ProductClass {
        config false;
        description
        "Identifier of the product class of the associated
        Internet Gateway Device.  {{empty}} indicates either
        that  there is no associated Internet Gateway Device
        that has been detected, or the Internet Gateway Device
        does not support the use of the  product-class
        parameter.";
        type string {
          length "0..64";
        }
      }
      leaf SerialNumber {
        config false;
        description
        "Serial number of the associated Internet Gateway
        Device.  {{empty}} indicates that there is no
        associated  Internet Gateway Device that has been
        detected.";
        type string {
          length "0..64";
        }
      }
    }
    container Time {
      description
      "This object contains parameters relating an NTP or SNTP
      time client in the CPE.";
      leaf Enable {
        config true;
        description
        "Enables or disables the NTP or SNTP time client.";
        type boolean;
      }
      leaf Status {
        config false;
        description
        "The {{enum|Error}} value MAY be used by the CPE to
        indicate a locally defined error condition.";
        type enumeration {
          enum "Disabled";
          enum "Unsynchronized";
          enum "Synchronized";
          enum "Error_FailedToSynchronize";
          enum "Error";
        }
      }
      leaf NTPServer1 {
        config true;
        description
        "First NTP timeserver.  Either a host name or IP
        address.";
        type string {
          length "0..64";
        }
      }
      leaf NTPServer2 {
        config true;
        description
        "Second NTP timeserver.  Either a host name or IP
        address.";
        type string {
          length "0..64";
        }
      }
      leaf NTPServer3 {
        config true;
        description
        "Third NTP timeserver.  Either a host name or IP
        address.";
        type string {
          length "0..64";
        }
      }
      leaf NTPServer4 {
        config true;
        description
        "Fourth NTP timeserver.  Either a host name or IP
        address.";
        type string {
          length "0..64";
        }
      }
      leaf NTPServer5 {
        config true;
        description
        "Fifth NTP timeserver.  Either a host name or IP
        address.";
        type string {
          length "0..64";
        }
      }
      leaf CurrentLocalTime {
        config false;
        description
        "The current date and time in the CPE's local time zone.";
        type yang:date-and-time;
      }
      leaf LocalTimeZone {
        config true;
        description
        ": EST+5 EDT,M4.1.0/2,M10.5.0/2";
        type string {
          length "0..256";
        }
      }
    }
    container UserInterface {
      description
      "This object contains parameters relating to the user
      interface of the CPE.";
      leaf Enable {
        config true;
        description
        "Enables and disables the CPE's user interface.";
        type boolean;
        default "true";
      }
      leaf PasswordRequired {
        config true;
        description
        "Indicates whether or not the local user interface MUST
        require a password to be chosen by the user.  If
        {{false}}, the choice of  whether or not a password is
        used is left to the user.";
        type boolean;
      }
      leaf PasswordUserSelectable {
        config true;
        description
        "Indicates whether or not a password to protect the
        local user interface of the CPE MAY be selected by the
        user directly (i.e.
        {{param|.Users.User.{i}.Password}}), or MUST be equal
        to the password used by the LAN-side Auto-Configuration
        protocol (i.e.
        {{param|.LANConfigSecurity.ConfigPassword}}).";
        type boolean;
      }
      leaf PasswordReset {
        config true;
        description
        "When set to true, resets
        {{param|.LANConfigSecurity.ConfigPassword}} to its
        factory value.";
        type boolean;
      }
      leaf UpgradeAvailable {
        config true;
        description
        "Indicates that a CPE upgrade is available, allowing the
        CPE to display this information to the  user.";
        type boolean;
      }
      leaf WarrantyDate {
        config true;
        description
        "Indicates the date and time in UTC that the warranty
        associated with the CPE is to expire.";
        type yang:date-and-time;
      }
      leaf ISPName {
        config true;
        description
        "The name of the customer's ISP.";
        type string {
          length "0..64";
        }
      }
      leaf ISPHelpDesk {
        config true;
        description
        "The help desk phone number of the ISP.";
        type string {
          length "0..32";
        }
      }
      leaf ISPHomePage {
        config true;
        description
        "The URL of the ISP's home page.";
        type string {
          length "0..256";
        }
      }
      leaf ISPHelpPage {
        config true;
        description
        "The URL of the ISP's on-line support page.";
        type string {
          length "0..256";
        }
      }
      leaf ISPLogo {
        config true;
        description
        "Base64 encoded GIF or JPEG image.  The binary image is
        constrained to 4095 bytes or less.";
        type binary {
          length "0..4095";
        }
      }
      leaf ISPLogoSize {
        config true;
        description
        "ISPLogoSize can also be used as a check to verify
        correct transfer and conversion of Base64 string to
        image size.";
        type uint32 {
          range "0..4095";
        }
      }
      leaf ISPMailServer {
        config true;
        description
        "The URL of the ISP's mail server.";
        type string {
          length "0..256";
        }
      }
      leaf ISPNewsServer {
        config true;
        description
        "The URL of the ISP's news server.";
        type string {
          length "0..256";
        }
      }
      leaf TextColor {
        config true;
        description
        "The color of text on the GUI screens in RGB hexadecimal
        notation (e.g., FF0088).";
        type yang:hex-string {
          length "3";
        }
      }
      leaf BackgroundColor {
        config true;
        description
        "The color of the GUI screen backgrounds in RGB
        hexadecimal notation (e.g., FF0088).";
        type yang:hex-string {
          length "3";
        }
      }
      leaf ButtonColor {
        config true;
        description
        "The color of buttons on the GUI screens in RGB
        hexadecimal notation (e.g., FF0088).";
        type yang:hex-string {
          length "3";
        }
      }
      leaf ButtonTextColor {
        config true;
        description
        "The color of text on buttons on the GUI screens in RGB
        hexadecimal notation (e.g., FF0088).";
        type yang:hex-string {
          length "3";
        }
      }
      leaf AutoUpdateServer {
        config true;
        description
        "This MUST NOT be used by the CPE if the
        {{param|.ManagementServer.UpgradesManaged}} parameter
        is {{true}}.";
        type string {
          length "0..256";
        }
      }
      leaf UserUpdateServer {
        config true;
        description
        "This MUST NOT be used by the CPE if the
        {{param|.ManagementServer.UpgradesManaged}} parameter
        is {{true}}.";
        type string {
          length "0..256";
        }
      }
      leaf-list AvailableLanguages {
        config false;
        description
        "{{list}} List items represent user-interface languages
        that are available, where each language is specified
        according to {{bibref|RFC3066}}.";
        type string;
      }
      leaf CurrentLanguage {
        config true;
        description
        "Current user-interface language, specified according to
        {{bibref|RFC3066}}. The value MUST be a member of the
        list reported by the {{param|AvailableLanguages}}
        parameter.";
        type string {
          length "0..16";
        }
      }
      container RemoteAccess {
        description
        "Remote access requires user authentication.  To provide
        remote access authentication the CPE MUST support a
        \"User\" table with at least one instance that has
        \"RemoteAccessCapable\" set to {{true}}.";
        leaf Enable {
          config true;
          description
          "Enables/Disables remotely accessing the CPE's user
          interface.";
          type boolean;
        }
        leaf Port {
          config true;
          description
          "Destination TCP port required for remote access
          connection.";
          type uint32 {
            range "min..65535";
          }
        }
        leaf-list SupportedProtocols {
          config false;
          description
          "{{list}} Indicates the protocols that are supported
          by the CPE for the purpose of remotely accessing the
          user interface.";
          type enumeration {
            enum "HTTP" {
              description
              "As defined in {{bibref|RFC2616}}";
            }
            enum "HTTPS" {
              description
              "As defined in {{bibref|RFC2818}}";
            }
          }
        }
        leaf Protocol {
          config true;
          description
          "This is the protocol currently being used for remote
          access.";
          type string;
          must ". = ../SupportedProtocols";
        }
      }
      container LocalDisplay {
        description
        "This object describes how to remotely manage the
        initial positioning of a user interface on a device's
        local display.";
        leaf Movable {
          config true;
          description
          "Controls whether the user is allowed to change the
          GUI window position on the local CPE's display.";
          type boolean;
        }
        leaf Resizable {
          config true;
          description
          "Controls whether the user is allowed to resize the
          GUI window on the local CPE's display.";
          type boolean;
        }
        leaf PosX {
          config true;
          description
          "The horizontal position of the User Interface's top
          left corner within the local CPE's display measured
          from the top left corner, expressed in {{units}}.";
          type int32;
        }
        leaf PosY {
          config true;
          description
          "The vertical position of the User Interface's top
          left corner within the local CPE's display measured
          from the top left corner, expressed in {{units}}.";
          type int32;
        }
        leaf Width {
          config true;
          description
          "The width of the user interface within the local
          CPE's display, expressed in {{units}}.";
          type uint32;
        }
        leaf Height {
          config true;
          description
          "The height of the user interface within the local
          CPE's display, expressed in {{units}}.";
          type uint32;
        }
        leaf DisplayWidth {
          config false;
          description
          "The width of the local CPE's display, expressed in
          {{units}}.";
          type uint32;
        }
        leaf DisplayHeight {
          config false;
          description
          "The height of the local CPE's display, expressed in
          {{units}}.";
          type uint32;
        }
      }
      container Messages {
        description
        "Definition of user information message displays.";
        leaf Enable {
          config true;
          description
          "Enables and displays the user information message.";
          type boolean;
          default "true";
        }
        leaf Title {
          config true;
          description
          "Message title to be displayed.";
          type string {
            length "0..128";
          }
        }
        leaf SubTitle {
          config true;
          description
          "Message sub title to be displayed.";
          type string {
            length "0..128";
          }
        }
        leaf Text {
          config true;
          description
          "Message text.";
          type string;
        }
        leaf IconType {
          config true;
          description
          "Icon to be displayed.";
          type enumeration {
            enum "None";
            enum "Greeting";
            enum "Information";
            enum "Warning";
            enum "Important";
            enum "Urgent";
            enum "Advertisement";
          }
        }
        leaf MessageColor {
          config true;
          description
          "The color of message text in RGB hexadecimal notation
          (e.g., FF0088).";
          type yang:hex-string {
            length "3";
          }
        }
        leaf BackgroundColor {
          config true;
          description
          "The color of the message screen background in RGB
          hexadecimal notation (e.g., FF0088).";
          type yang:hex-string {
            length "3";
          }
        }
        leaf TitleColor {
          config true;
          description
          "The color of the message title in RGB hexadecimal
          notation (e.g., FF0088).";
          type yang:hex-string {
            length "3";
          }
        }
        leaf SubTitleColor {
          config true;
          description
          "The color of the sub title in RGB hexadecimal
          notation (e.g., FF0088).";
          type yang:hex-string {
            length "3";
          }
        }
        leaf RequestedNumberOfRepetitions {
          config true;
          description
          "The number of times the device SHOULD repeat the
          message.";
          type uint32;
        }
        leaf ExecutedNumberOfRepetitions {
          config false;
          description
          "The number of times the device repeated the message.";
          type uint32;
        }
      }
    }
    list InterfaceStack {
      key "HigherLayer LowerLayer";
      unique "Alias";
      config true;
      description
      "Each table row represents a \"link\" between two
      interface objects, a higher-layer interface object
      (referenced by {{param|HigherLayer}}) and a lower-layer
      interface object (referenced by {{param|LowerLayer}}).
      Consequently, if a referenced interface object is
      deleted, the CPE MUST delete the corresponding {{object}}
      row(s) that had referenced it.";
      leaf Alias {
        config true;
        description
        "{{datatype|expand}}";
        type Alias;
      }
      leaf HigherLayer {
        config true;
        description
        "When the referenced higher layer interface is deleted,
        the CPE MUST delete the table row.";
        type string {
          length "0..256";
        }
      }
      leaf LowerLayer {
        config true;
        description
        "When the referenced lower layer interface is deleted,
        the CPE MUST delete the table row.";
        type string {
          length "0..256";
        }
      }
      leaf HigherAlias {
        config false;
        description
        "The value of the ''Alias'' parameter for the interface
        object referenced by {{param|HigherLayer}}.";
        type string {
          length "0..64";
        }
      }
      leaf LowerAlias {
        config false;
        description
        "The value of the ''Alias'' parameter for the interface
        object referenced by {{param|LowerLayer}}.";
        type string {
          length "0..64";
        }
      }
    }
    container DSL {
      description
      "This object models DSL lines, DSL channels, DSL bonding,
      and DSL diagnostics.  The specific interface objects
      defined here are {{object|Line}}, {{object|Channel}}, and
      {{object|BondingGroup}}. Each {{object|Line}} models a
      layer 1 DSL Line interface, and each {{object|Channel}}
      models a layer 1 DSL Channel interface where multiple
      channels can run over a DSL line.  In the case where
      bonding is configured, it is expected that
      {{object|BondingGroup}} is stacked above the
      {{object|Channel}} instances within its group.";
      leaf LineNumberOfEntries {
        config false;
        description
        "{{numentries}}";
        type uint32;
      }
      leaf ChannelNumberOfEntries {
        config false;
        description
        "{{numentries}}";
        type uint32;
      }
      leaf BondingGroupNumberOfEntries {
        config false;
        description
        "{{numentries}}";
        type uint32;
      }
      list Line {
        key "Name";
        unique "Alias";
        config true;
        description
        "This table models physical DSL lines.";
        leaf Enable {
          config true;
          description
          "This parameter is based on ''ifAdminStatus'' from
          {{bibref|RFC2863}}.";
          type boolean;
        }
        leaf EnableDataGathering {
          config true;
          description
          "Enables or disables data gathering on the DSL line.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config true;
          description
          "The textual name of the DSL line as assigned by the
          CPE.";
          type string {
            length "0..64";
          }
        }
        leaf LastChange {
          config false;
          description
          "The accumulated time in {{units}} since the DSL line
          entered its current operational state.";
          type uint32;
        }
        leaf-list LowerLayers {
          config true;
          description
          "Note: Since {{object}} is a layer 1 interface, it is
          expected that {{param}} will not be used.";
          type string;
        }
        leaf Upstream {
          config false;
          description
          "* For an End Device, {{param}} will be {{true}} for
          all interfaces.";
          type boolean;
        }
        leaf FirmwareVersion {
          config false;
          description
          "A string identifying the version of the modem
          firmware currently installed for this interface.
          This is applicable only when the modem firmware is
          separable from the overall CPE software.";
          type string {
            length "0..64";
          }
        }
        leaf LinkStatus {
          config false;
          description
          "The {{enum|Error}} value MAY be used by the CPE to
          indicate a locally defined error condition.";
          type enumeration {
            enum "Up";
            enum "Initializing";
            enum "EstablishingLink";
            enum "NoSignal";
            enum "Disabled";
            enum "Error";
          }
        }
        leaf-list StandardsSupported {
          config false;
          description
          "This parameter is DEPRECATED because its entries are
          out-of-date; {{param|XTSE}} points to a current list.
          Therefore its value MAY be {{empty}} if (and only if)
          {{param|XTSE}} is supported.";
          type enumeration {
            enum "G.992.1_Annex_A";
            enum "G.992.1_Annex_B";
            enum "G.992.1_Annex_C";
            enum "T1.413";
            enum "T1.413i2";
            enum "ETSI_101_388";
            enum "G.992.2";
            enum "G.992.3_Annex_A";
            enum "G.992.3_Annex_B";
            enum "G.992.3_Annex_C";
            enum "G.992.3_Annex_I";
            enum "G.992.3_Annex_J";
            enum "G.992.3_Annex_L";
            enum "G.992.3_Annex_M";
            enum "G.992.4";
            enum "G.992.5_Annex_A";
            enum "G.992.5_Annex_B";
            enum "G.992.5_Annex_C";
            enum "G.992.5_Annex_I";
            enum "G.992.5_Annex_J";
            enum "G.992.5_Annex_M";
            enum "G.993.1";
            enum "G.993.1_Annex_A";
            enum "G.993.2_Annex_A";
            enum "G.993.2_Annex_B";
            enum "G.993.2_Annex_C";
          }
        }
        leaf XTSE {
          config false;
          description
          "Note: This parameter is defined as xDSL Transmission
          system enabling (XTSE) in ITU-T G.997.1. For a full
          definition, see Clause 7.3.1.1.1 of ITU-T
          Recommendation {{bibref|G.997.1}}.";
          type yang:hex-string {
            length "8";
          }
        }
        leaf StandardUsed {
          config false;
          description
          "This parameter is DEPRECATED because its entries are
          out-of-date; {{param|XTSE}} points to a current list.
          Therefore its value MAY be {{empty}} if (and only if)
          {{param|XTSUsed}} is supported.";
          type string;
          must ". = ../StandardsSupported";
        }
        leaf XTSUsed {
          config false;
          description
          "This parameter indicates which DSL standard and
          recommendation are currently in use by the {{object}}
          instance.  Only one bit is set, as defined for the
          xTU transmission system enabling (XTSE) in ITU-T
          G.997.1.";
          type yang:hex-string {
            length "8";
          }
        }
        leaf LineEncoding {
          config false;
          description
          "Note: Generally speaking, this variable does not
          change after provisioning.";
          type enumeration {
            enum "DMT";
            enum "CAP";
            enum "2B1Q";
            enum "43BT";
            enum "PAM";
            enum "QAM";
          }
        }
        leaf-list AllowedProfiles {
          config false;
          description
          "Note: This parameter is OPTIONAL at the G and S/T
          interfaces in G.997.1 Amendment 1.  If the parameter
          is implemented but no value is  available, its value
          MUST be {{empty}}.";
          type enumeration {
            enum "8a";
            enum "8b";
            enum "8c";
            enum "8d";
            enum "12a";
            enum "12b";
            enum "17a";
            enum "17b";
            enum "30a";
            enum "35b";
          }
        }
        leaf CurrentProfile {
          config false;
          description
          "Note: This parameter is OPTIONAL at the G and S/T
          interfaces in G.997.1 Amendment 1.  If the parameter
          is implemented but no value is  available, its value
          MUST be {{empty}}.";
          type string;
          must ". = ../AllowedProfiles";
        }
        leaf PowerManagementState {
          config false;
          description
          "Note: See ITU-T Recommendation {{bibref|G.997.1}}.";
          type enumeration {
            enum "L0";
            enum "L1";
            enum "L2";
            enum "L3";
            enum "L4";
          }
        }
        leaf SuccessFailureCause {
          config false;
          description
          "Note: In G.997.1, this parameter is called
          \"Initialization success/failure cause\". See Clause
          7.5.1.6 of ITU-T Recommendation {{bibref|G.997.1}}.";
          type uint32 {
            range "0..6";
          }
        }
        leaf UPBOKLER {
          config false;
          description
          "Note: This parameter is defined as UPBOKLE-R in
          Clause 7.5.1.23.2 of ITU-T Recommendation
          {{bibref|G.997.1}}.";
          type uint32 {
            range "0..1280";
          }
        }
        leaf-list UPBOKLEPb {
          config false;
          description
          "Note: This parameter is defined as UPBOKLE-pb in
          Clause 7.5.1.23.3 of ITU-T Recommendation
          {{bibref|G.997.1}}.";
          type uint32 {
            range "0..1280|2047";
          }
        }
        leaf-list UPBOKLERPb {
          config false;
          description
          "Note: This parameter is defined as UPBOKLE-R-pb in
          Clause 7.5.1.23.4 of ITU-T Recommendation
          {{bibref|G.997.1}}.";
          type uint32 {
            range "0..1280|2047";
          }
        }
        leaf RXTHRSHds {
          config false;
          description
          "Note: See ITU-T Recommendation {{bibref|G.997.1}}.";
          type int32 {
            range "-640..0";
          }
        }
        leaf ACTRAMODEds {
          config false;
          description
          "Note: This parameter is defined as ACT-RA-MODEds in
          Clause 7.5.1.33.1 of ITU-T Recommendation
          {{bibref|G.997.1}}.";
          type uint32 {
            range "1..4";
          }
        }
        leaf ACTRAMODEus {
          config false;
          description
          "Note: This parameter is defined as ACT-RA-MODEus in
          Clause 7.5.1.33.2 of ITU-T Recommendation
          {{bibref|G.997.1}}.";
          type uint32 {
            range "1..4";
          }
        }
        leaf ACTINPROCds {
          config false;
          description
          "Note: This parameter is defined as ACTINP-ROC-ds in
          Clause 7.5.1.34.1 of ITU-T Recommendation
          {{bibref|G.997.1}}.";
          type uint32;
        }
        leaf ACTINPROCus {
          config false;
          description
          "Note: This parameter is defined as ACTINP-ROC-us in
          Clause 7.5.1.34.2 ITU-T Recommendation
          {{bibref|G.997.1}}.";
          type uint32;
        }
        leaf SNRMROCds {
          config false;
          description
          "Note: This parameter is defined as SNRM-ROC-ds in
          Clause 7.5.1.35.1 ITU-T Recommendation
          {{bibref|G.997.1}}.";
          type uint32;
        }
        leaf SNRMROCus {
          config false;
          description
          "Note: This parameter is defined as SNRM-ROC-us in
          Clause 7.5.1.35.2 ITU-T Recommendation
          {{bibref|G.997.1}}.";
          type uint32;
        }
        leaf LastStateTransmittedDownstream {
          config false;
          description
          "Note: See ITU-T Recommendation {{bibref|G.997.1}}.";
          type uint32;
        }
        leaf LastStateTransmittedUpstream {
          config false;
          description
          "Note: See ITU-T Recommendation {{bibref|G.997.1}}.";
          type uint32;
        }
        leaf UPBOKLE {
          config false;
          description
          "Note: See ITU-T Recommendation {{bibref|G.997.1}}.";
          type uint32 {
            range "0..1280";
          }
        }
        leaf MREFPSDds {
          config false;
          description
          "Note: See ITU-T Recommendation {{bibref|G.997.1}}.";
          type binary {
            length "0..145";
          }
        }
        leaf MREFPSDus {
          config false;
          description
          "Note: See ITU-T Recommendation {{bibref|G.997.1}}.";
          type binary {
            length "0..145";
          }
        }
        leaf LIMITMASK {
          config false;
          description
          "Note: See ITU-T Recommendation {{bibref|G.997.1}}.";
          type uint32;
        }
        leaf US0MASK {
          config false;
          description
          "Note: See ITU-T Recommendation {{bibref|G.997.1}}.";
          type uint32;
        }
        leaf TRELLISds {
          config false;
          description
          "Note:  See ITU-T Recommendation {{bibref|G.997.1}}.
          For a multimode device operating in a mode in which
          this parameter does not apply, the value  of this
          parameter SHOULD be set to -1.";
          type int32;
        }
        leaf TRELLISus {
          config false;
          description
          "Note:  See ITU-T Recommendation {{bibref|G.997.1}}.
          For a multimode device operating in a mode in which
          this parameter does not apply, the value  of this
          parameter SHOULD be set to -1.";
          type int32;
        }
        leaf ACTSNRMODEds {
          config false;
          description
          "Note:  See ITU-T Recommendation {{bibref|G.997.1}}.
          For a multimode device operating in a mode in which
          this parameter does not apply, the value  of this
          parameter SHOULD be set to 0.";
          type uint32;
        }
        leaf ACTSNRMODEus {
          config false;
          description
          "Note:  See ITU-T Recommendation {{bibref|G.997.1}}.
          For a multimode device operating in a mode in which
          this parameter does not apply, the value  of this
          parameter SHOULD be set to 0.";
          type uint32;
        }
        leaf VirtualNoisePSDds {
          config false;
          description
          "See ITU-T Recommendation {{bibref|G.997.1}}. For a
          multimode device operating in a mode in which this
          parameter does not apply, the value of  this
          parameter SHOULD be set to {{empty}}.";
          type binary {
            length "0..97";
          }
        }
        leaf VirtualNoisePSDus {
          config false;
          description
          "See ITU-T Recommendation {{bibref|G.997.1}}. For a
          multimode device operating in a mode in which this
          parameter does not apply, the value of  this
          parameter SHOULD be set to {{empty}}.";
          type binary {
            length "0..49";
          }
        }
        leaf ACTUALCE {
          config false;
          description
          "Note:  See ITU-T Recommendation {{bibref|G.997.1}}.
          For a multimode device operating in a mode in which
          this parameter does not apply, the value  of this
          parameter SHOULD be set to 99.";
          type uint32;
        }
        leaf LineNumber {
          config false;
          description
          "Signifies the line pair that the modem is using to
          connection.  {{param}} = 1 is the innermost  pair.";
          type int32 {
            range "1..max";
          }
        }
        leaf UpstreamMaxBitRate {
          config false;
          description
          "Note:  This parameter is related to the G.997.1
          parameter ATTNDRus, which is measured in bits/s.  See
          ITU-T Recommendation {{bibref|G.997.1}}.";
          type uint32;
        }
        leaf DownstreamMaxBitRate {
          config false;
          description
          "Note:  This parameter is related to the G.997.1
          parameter ATTNDRds, which is measured in bits/s.  See
          ITU-T Recommendation {{bibref|G.997.1}}.";
          type uint32;
        }
        leaf UpstreamNoiseMargin {
          config false;
          description
          "Note:  In G.997.1, this parameter is called SNRMus.
          See ITU-T Recommendation {{bibref|G.997.1}}.";
          type int32;
        }
        leaf DownstreamNoiseMargin {
          config false;
          description
          "Note:  In G.997.1, this parameter is called SNRMds.
          See ITU-T Recommendation {{bibref|G.997.1}}.";
          type int32;
        }
        leaf-list SNRMpbus {
          config false;
          description
          "Note:  See ITU-T Recommendation {{bibref|G.997.1}}.";
          type string;
        }
        leaf-list SNRMpbds {
          config false;
          description
          "Note:  See ITU-T Recommendation {{bibref|G.997.1}}.";
          type string;
        }
        leaf INMIATOds {
          config false;
          description
          "Note:  In G.997.1, this parameter is called INMIATO.
          See ITU-T Recommendation {{bibref|G.997.1}}.";
          type uint32 {
            range "3..511";
          }
        }
        leaf INMIATSds {
          config false;
          description
          "Note:  In G.997.1, this parameter is called INMIATS.
          See ITU-T Recommendation {{bibref|G.997.1}}.";
          type uint32 {
            range "0..7";
          }
        }
        leaf INMCCds {
          config false;
          description
          "Note:  In G.997.1, this parameter is called INMCC.
          See ITU-T Recommendation {{bibref|G.997.1}}.";
          type uint32 {
            range "0..64";
          }
        }
        leaf INMINPEQMODEds {
          config false;
          description
          "Note:  In G.997.1, this parameter is called
          INM_INPEQ_MODE.  See ITU-T Recommendation
          {{bibref|G.997.1}}.";
          type uint32 {
            range "0..3";
          }
        }
        leaf UpstreamAttenuation {
          config false;
          description
          "Doesn't apply to VDSL2 {{bibref|G.993.2}}. Otherwise
          has the same value as the single element of
          {{param|TestParams.SATNus}}.";
          type int32;
        }
        leaf DownstreamAttenuation {
          config false;
          description
          "Doesn't apply to VDSL2 {{bibref|G.993.2}}. Otherwise
          has the same value as the single element of
          {{param|TestParams.SATNds}}.";
          type int32;
        }
        leaf UpstreamPower {
          config false;
          description
          "The current output power at the CPE's DSL line
          (expressed in {{units}}).";
          type int32;
        }
        leaf DownstreamPower {
          config false;
          description
          "The current received power at the CPE's DSL line
          (expressed in {{units}}).";
          type int32;
        }
        leaf XTURVendor {
          config false;
          description
          "Note: In G.997.1, this parameter is called \"xTU-R
          G.994.1 Vendor ID\". See ITU-T Recommendation
          {{bibref|G.997.1}}.";
          type yang:hex-string {
            length "4";
          }
        }
        leaf XTURCountry {
          config false;
          description
          "Note: In G.997.1, this parameter is called \"xTU-R
          G.994.1 Vendor ID\". See ITU-T Recommendation
          {{bibref|G.997.1}}.";
          type yang:hex-string {
            length "2";
          }
        }
        leaf XTURANSIStd {
          config false;
          description
          "When T1.413 modulation is not in use, the parameter
          value SHOULD be 0.";
          type uint32;
        }
        leaf XTURANSIRev {
          config false;
          description
          "When T1.413 modulation is not in use, the parameter
          value SHOULD be 0.";
          type uint32;
        }
        leaf XTUCVendor {
          config false;
          description
          "Note: This parameter is OPTIONAL at the G and S/T
          interfaces in G.997.1 Amendment 1.  If the parameter
          is implemented but no value is  available, it MUST
          have the value \"00000000\".";
          type yang:hex-string {
            length "4";
          }
        }
        leaf XTUCCountry {
          config false;
          description
          "Note: This parameter is OPTIONAL at the G and S/T
          interfaces in G.997.1 Amendment 1.  If the parameter
          is implemented but no value is  available, it MUST
          have the value \"0000\".";
          type yang:hex-string {
            length "2";
          }
        }
        leaf XTUCANSIStd {
          config false;
          description
          "When T1.413 modulation is not in use, the parameter
          value SHOULD be 0.";
          type uint32;
        }
        leaf XTUCANSIRev {
          config false;
          description
          "When T1.413 modulation is not in use, the parameter
          value SHOULD be 0.";
          type uint32;
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to prevent their being delivered.
            One possible reason for discarding such a packet
            could be to free up buffer space.";
            type uint32;
          }
          leaf TotalStart {
            config false;
            description
            "Note: {{param}} SHOULD NOT be reset when the
            interface statistics are reset via an interface
            disable / enable cycle.";
            type uint32;
          }
          leaf ShowtimeStart {
            config false;
            description
            "Note: {{param}} SHOULD NOT be reset when the
            interface statistics are reset via an interface
            disable / enable cycle.";
            type uint32;
          }
          leaf LastShowtimeStart {
            config false;
            description
            "Note: {{param}} SHOULD NOT be reset when the
            interface statistics are reset via an interface
            disable / enable cycle.";
            type uint32;
          }
          leaf CurrentDayStart {
            config false;
            description
            "Note: {{param}} SHOULD NOT be reset when the
            interface statistics are reset via an interface
            disable / enable cycle.";
            type uint32;
          }
          leaf QuarterHourStart {
            config false;
            description
            "Note: {{param}} SHOULD NOT be reset when the
            interface statistics are reset via an interface
            disable / enable cycle.";
            type uint32;
          }
          container Total {
            description
            "Note: The {{object}} parameters SHOULD NOT be reset
            when the interface statistics are reset via an
            interface disable / enable cycle.";
            leaf ErroredSecs {
              config false;
              description
              "Note: This parameter is OPTIONAL at the G and S/T
              interfaces in G.997.1 Amendment 1.  If the
              parameter is implemented but no value is
              available, its value MUST be 4294967295 (the
              maximum for its data type).";
              type uint32;
            }
            leaf SeverelyErroredSecs {
              config false;
              description
              "Note: This parameter is OPTIONAL at the G and S/T
              interfaces in G.997.1 Amendment 1.  If the
              parameter is implemented but no value is
              available, its value MUST be 4294967295 (the
              maximum for its data type).";
              type uint32;
            }
          }
          container Showtime {
            description
            "Note: The {{object}} parameters SHOULD NOT be reset
            when the interface statistics are reset via an
            interface disable / enable cycle.";
            leaf ErroredSecs {
              config false;
              description
              "Note: This parameter is OPTIONAL at the G and S/T
              interfaces in G.997.1 Amendment 1.  If the
              parameter is implemented but no value is
              available, its value MUST be 4294967295 (the
              maximum for its data type).";
              type uint32;
            }
            leaf SeverelyErroredSecs {
              config false;
              description
              "Note: This parameter is OPTIONAL at the G and S/T
              interfaces in G.997.1 Amendment 1.  If the
              parameter is implemented but no value is
              available, its value MUST be 4294967295 (the
              maximum for its data type).";
              type uint32;
            }
          }
          container LastShowtime {
            description
            "Note: The {{object}} parameters SHOULD NOT be reset
            when the interface statistics are reset via an
            interface disable / enable cycle.";
            leaf ErroredSecs {
              config false;
              description
              "Note: This parameter is OPTIONAL at the G and S/T
              interfaces in G.997.1 Amendment 1.  If the
              parameter is implemented but no value is
              available, its value MUST be 4294967295 (the
              maximum for its data type).";
              type uint32;
            }
            leaf SeverelyErroredSecs {
              config false;
              description
              "Note: This parameter is OPTIONAL at the G and S/T
              interfaces in G.997.1 Amendment 1.  If the
              parameter is implemented but no value is
              available, its value MUST be 4294967295 (the
              maximum for its data type).";
              type uint32;
            }
          }
          container CurrentDay {
            description
            "Note: The {{object}} parameters SHOULD NOT be reset
            when the interface statistics are reset via an
            interface disable / enable cycle.";
            leaf ErroredSecs {
              config false;
              description
              "Note: This parameter is OPTIONAL at the G and S/T
              interfaces in G.997.1 Amendment 1.  If the
              parameter is implemented but no value is
              available, its value MUST be 4294967295 (the
              maximum for its data type).";
              type uint32;
            }
            leaf SeverelyErroredSecs {
              config false;
              description
              "Note: This parameter is OPTIONAL at the G and S/T
              interfaces in G.997.1 Amendment 1.  If the
              parameter is implemented but no value is
              available, its value MUST be 4294967295 (the
              maximum for its data type).";
              type uint32;
            }
          }
          container QuarterHour {
            description
            "Note: The {{object}} parameters SHOULD NOT be reset
            when the interface statistics are reset via an
            interface disable / enable cycle.";
            leaf ErroredSecs {
              config false;
              description
              "Note: This parameter is OPTIONAL at the G and S/T
              interfaces in G.997.1 Amendment 1.  If the
              parameter is implemented but no value is
              available, its value MUST be 4294967295 (the
              maximum for its data type).";
              type uint32;
            }
            leaf SeverelyErroredSecs {
              config false;
              description
              "Note: This parameter is OPTIONAL at the G and S/T
              interfaces in G.997.1 Amendment 1.  If the
              parameter is implemented but no value is
              available, its value MUST be 4294967295 (the
              maximum for its data type).";
              type uint32;
            }
          }
        }
        container TestParams {
          description
          "This object contains the DSL line test parameters
          that are available during the L0 (i.e., Showtime)
          state.";
          leaf HLOGGds {
            config false;
            description
            "Note:  See ITU-T Recommendation {{bibref|G.997.1}}.
            For a multimode device operating in a mode in which
            this parameter does not apply, the value  of this
            parameter SHOULD be set to 1.";
            type uint32;
          }
          leaf HLOGGus {
            config false;
            description
            "Note:  See ITU-T Recommendation {{bibref|G.997.1}}.
            For a multimode device operating in a mode in which
            this parameter does not apply, the value  of this
            parameter SHOULD be set to 1.";
            type uint32;
          }
          leaf-list HLOGpsds {
            config false;
            description
            "Note: {{param}} is measured during initialization
            and is not updated during Showtime.";
            type string;
          }
          leaf-list HLOGpsus {
            config false;
            description
            "Note: {{param}} is measured during initialization
            and is not updated during Showtime.";
            type string;
          }
          leaf HLOGMTds {
            config false;
            description
            "Note:  See ITU-T Recommendation {{bibref|G.997.1}}.
            For a multimode device operating in a mode in which
            this parameter does not apply, the value  of this
            parameter SHOULD be set to 0.";
            type uint32;
          }
          leaf HLOGMTus {
            config false;
            description
            "Note:  See ITU-T Recommendation {{bibref|G.997.1}}.
            For a multimode device operating in a mode in which
            this parameter does not apply, the value  of this
            parameter SHOULD be set to 0.";
            type uint32;
          }
          leaf QLNGds {
            config false;
            description
            "Note:  See ITU-T Recommendation {{bibref|G.997.1}}.
            For a multimode device operating in a mode in which
            this parameter does not apply, the value  of this
            parameter SHOULD be set to 1.";
            type uint32;
          }
          leaf QLNGus {
            config false;
            description
            "Note:  See ITU-T Recommendation {{bibref|G.997.1}}.
            For a multimode device operating in a mode in which
            this parameter does not apply, the value  of this
            parameter SHOULD be set to 1.";
            type uint32;
          }
          leaf-list QLNpsds {
            config false;
            description
            "Note: {{param}} is measured during initialization
            and is not updated during Showtime.";
            type int32;
          }
          leaf-list QLNpsus {
            config false;
            description
            "Note: {{param}} is measured during initialization
            and is not updated during Showtime.";
            type string;
          }
          leaf QLNMTds {
            config false;
            description
            "Note:  See ITU-T Recommendation {{bibref|G.997.1}}.
            For a multimode device operating in a mode in which
            this parameter does not apply, the value  of this
            parameter SHOULD be set to 0.";
            type uint32;
          }
          leaf QLNMTus {
            config false;
            description
            "Note:  See ITU-T Recommendation {{bibref|G.997.1}}.
            For a multimode device operating in a mode in which
            this parameter does not apply, the value  of this
            parameter SHOULD be set to 0.";
            type uint32;
          }
          leaf SNRGds {
            config false;
            description
            "Note:  See ITU-T Recommendation {{bibref|G.997.1}}.
            For a multimode device operating in a mode in which
            this parameter does not apply, the value  of this
            parameter SHOULD be set to 1.";
            type uint32;
          }
          leaf SNRGus {
            config false;
            description
            "Note:  See ITU-T Recommendation {{bibref|G.997.1}}.
            For a multimode device operating in a mode in which
            this parameter does not apply, the value  of this
            parameter SHOULD be set to 1.";
            type uint32;
          }
          leaf-list SNRpsds {
            config false;
            description
            "Note: {{param}} is first measured during
            initialization and is updated during Showtime.";
            type int32;
          }
          leaf-list SNRpsus {
            config false;
            description
            "Note: {{param}} is first measured during
            initialization and is updated during Showtime.";
            type string;
          }
          leaf SNRMTds {
            config false;
            description
            "Note:  See ITU-T Recommendation {{bibref|G.997.1}}.
            For a multimode device operating in a mode in which
            this parameter does not apply, the value  of this
            parameter SHOULD be set to 0.";
            type uint32;
          }
          leaf SNRMTus {
            config false;
            description
            "Note:  See ITU-T Recommendation {{bibref|G.997.1}}.
            For a multimode device operating in a mode in which
            this parameter does not apply, the value  of this
            parameter SHOULD be set to 0.";
            type uint32;
          }
          leaf-list LATNds {
            config false;
            description
            "Note:  See ITU-T Recommendation {{bibref|G.997.1}}.";
            type string;
          }
          leaf-list LATNus {
            config false;
            description
            "Note:  See ITU-T Recommendation {{bibref|G.997.1}}.";
            type string;
          }
          leaf-list SATNds {
            config false;
            description
            "Note:  See ITU-T Recommendation {{bibref|G.997.1}}.";
            type string;
          }
          leaf-list SATNus {
            config false;
            description
            "Note:  See ITU-T Recommendation {{bibref|G.997.1}}.";
            type string;
          }
        }
        container DataGathering {
          description
          "Note: see ITU-T Recommendation {{bibref|G.993.2}}.";
          leaf LoggingDepthR {
            config false;
            description
            "Note: This parameter is defined as LOGGING_DEPTH_R
            in Clause 7.5.3.2 of ITU-T Recommendation
            {{bibref|G.997.1}}.";
            type uint32;
          }
          leaf ActLoggingDepthReportingR {
            config false;
            description
            "Note: This parameter is defined as
            ACT_LOGGING_DEPTH_REPORTING_R in Clause 7.5.3.4 of
            ITU-T Recommendation {{bibref|G.997.1}}.";
            type uint32;
          }
          leaf EventTraceBufferR {
            config false;
            description
            "Note: This parameter is defined as
            EVENT_TRACE_BUFFER_R in Clause 7.5.3.6 of ITU-T
            Recommendation {{bibref|G.997.1}} and Clause 11.5
            of ITU-T Recommendation {{bibref|G.993.2}}.";
            type string {
              length "0..256";
            }
          }
        }
      }
      list Channel {
        key "Name";
        unique "Alias";
        config true;
        description
        "This table models DSL channel(s) on top of physical DSL
        lines.";
        leaf Enable {
          config true;
          description
          "This parameter is based on ''ifAdminStatus'' from
          {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config true;
          description
          "The textual name of the channel as assigned by the
          CPE.";
          type string {
            length "0..64";
          }
        }
        leaf LastChange {
          config false;
          description
          "The accumulated time in {{units}} since the channel
          entered its current operational state.";
          type uint32;
        }
        leaf-list LowerLayers {
          config false;
          description
          "{{list}} {{reference|an interface object that is
          stacked immediately below this interface object}}
          See {{bibref|TR-181i2|Section 4.2.1}}.";
          type string;
        }
        leaf-list LinkEncapsulationSupported {
          config false;
          description
          "{{list}} List items indicate which link encapsulation
          standards and recommendations are supported by the
          {{object}} instance.";
          type enumeration {
            enum "G.992.3_Annex_K_ATM";
            enum "G.992.3_Annex_K_PTM";
            enum "G.993.2_Annex_K_ATM";
            enum "G.993.2_Annex_K_PTM";
            enum "G.994.1" {
              description
              "Auto";
            }
          }
        }
        leaf LinkEncapsulationUsed {
          config false;
          description
          "When PTM encapsulation is identified then an
          upper-layer {{object|.PTM.Link}} interface MUST be
          used.";
          type enumeration {
            enum "G.992.3_Annex_K_ATM";
            enum "G.992.3_Annex_K_PTM";
            enum "G.993.2_Annex_K_ATM";
            enum "G.993.2_Annex_K_PTM";
          }
        }
        leaf LPATH {
          config false;
          description
          "Note:  See ITU-T Recommendation
          {{bibref|G.997.1|Section 7.5.2.7}}.";
          type uint32 {
            range "min..3";
          }
        }
        leaf INTLVDEPTH {
          config false;
          description
          "Note:  See ITU-T Recommendation {{bibref|G.997.1}}.
          For a multimode device operating in a mode in which
          this parameter does not apply, the value of this
          parameter SHOULD be set to 0.";
          type uint32;
        }
        leaf INTLVBLOCK {
          config false;
          description
          "Note:  See ITU-T Recommendation {{bibref|G.997.1}}.
          For a multimode device operating in a mode in which
          this parameter does not apply, the value  of this
          parameter SHOULD be set to -1.";
          type int32;
        }
        leaf ActualInterleavingDelay {
          config false;
          description
          "Note:  In G.997.1, this parameter is called \"Actual
          Interleaving Delay.\" See ITU-T Recommendation
          {{bibref|G.997.1}}.";
          type uint32;
        }
        leaf ACTINP {
          config false;
          description
          "Note:  See ITU-T Recommendation {{bibref|G.997.1}}.
          For a multimode device operating in a mode in which
          this parameter does not apply, the value  of this
          parameter SHOULD be set to -1.";
          type int32;
        }
        leaf INPREPORT {
          config false;
          description
          "Note:  See ITU-T Recommendation {{bibref|G.997.1}}.
          For a multimode device operating in a mode in which
          this parameter does not apply, the  value of this
          parameter SHOULD be set to {{false}}.";
          type boolean;
        }
        leaf NFEC {
          config false;
          description
          "Note:  See ITU-T Recommendation {{bibref|G.997.1}}.
          For a multimode device operating in a mode in which
          this parameter does not apply, the value  of this
          parameter SHOULD be set to -1.";
          type int32;
        }
        leaf RFEC {
          config false;
          description
          "Note:  See ITU-T Recommendation {{bibref|G.997.1}}.
          For a multimode device operating in a mode in which
          this parameter does not apply, the value  of this
          parameter SHOULD be set to -1.";
          type int32;
        }
        leaf LSYMB {
          config false;
          description
          "Note:  See ITU-T Recommendation {{bibref|G.997.1}}.
          For a multimode device operating in a mode in which
          this parameter does not apply, the value  of this
          parameter SHOULD be set to -1.";
          type int32;
        }
        leaf UpstreamCurrRate {
          config false;
          description
          "Note: If the parameter is implemented but no value is
          available, it MUST have the value 4294967295 (the
          maximum for its data type).";
          type uint32;
        }
        leaf DownstreamCurrRate {
          config false;
          description
          "Note: If the parameter is implemented but no value is
          available, it MUST have the value 4294967295 (the
          maximum for its data type).";
          type uint32;
        }
        leaf ACTNDR {
          config false;
          description
          "Note: See ITU-T Recommendation {{bibref|G.997.1}}.";
          type uint32;
        }
        leaf ACTINPREIN {
          config false;
          description
          "Note: This parameter is defined as ACTINP_REIN in
          Clause 7.5.2.9 of ITU-T Recommendation
          {{bibref|G.997.1}}.";
          type uint32 {
            range "0..255";
          }
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to prevent their being delivered.
            One possible reason for discarding such a packet
            could be to free up buffer space.";
            type uint32;
          }
          leaf TotalStart {
            config false;
            description
            "Note: {{param}} SHOULD NOT be reset when the
            interface statistics are reset via an interface
            disable / enable cycle.";
            type uint32;
          }
          leaf ShowtimeStart {
            config false;
            description
            "Note: {{param}} SHOULD NOT be reset when the
            interface statistics are reset via an interface
            disable / enable cycle.";
            type uint32;
          }
          leaf LastShowtimeStart {
            config false;
            description
            "Note: {{param}} SHOULD NOT be reset when the
            interface statistics are reset via an interface
            disable / enable cycle.";
            type uint32;
          }
          leaf CurrentDayStart {
            config false;
            description
            "Note: {{param}} SHOULD NOT be reset when the
            interface statistics are reset via an interface
            disable / enable cycle.";
            type uint32;
          }
          leaf QuarterHourStart {
            config false;
            description
            "Note: {{param}} SHOULD NOT be reset when the
            interface statistics are reset via an interface
            disable / enable cycle.";
            type uint32;
          }
          container Total {
            description
            "Note: The {{object}} parameters SHOULD NOT be reset
            when the interface statistics are reset via an
            interface disable / enable cycle.";
            leaf XTURFECErrors {
              config false;
              description
              "Note: If the parameter is implemented but no
              value is available, its value MUST be 4294967295
              (the maximum for its data type).";
              type uint32;
            }
            leaf XTUCFECErrors {
              config false;
              description
              "Note: If the parameter is implemented but no
              value is available, its value MUST be 4294967295
              (the maximum for its data type).";
              type uint32;
            }
            leaf XTURHECErrors {
              config false;
              description
              "Note: If the parameter is implemented but no
              value is  available, its value MUST be 4294967295
              (the maximum for its data type).";
              type uint32;
            }
            leaf XTUCHECErrors {
              config false;
              description
              "Note: If the parameter is implemented but no
              value is  available, its value MUST be 4294967295
              (the maximum for its data type).";
              type uint32;
            }
            leaf XTURCRCErrors {
              config false;
              description
              "Note: If the parameter is implemented but no
              value is  available, its value MUST be 4294967295
              (the maximum for its data type).";
              type uint32;
            }
            leaf XTUCCRCErrors {
              config false;
              description
              "Note: If the parameter is implemented but no
              value is  available, its value MUST be 4294967295
              (the maximum for its data type).";
              type uint32;
            }
          }
          container Showtime {
            description
            "Note: The {{object}} parameters SHOULD NOT be reset
            when the interface statistics are reset via an
            interface disable / enable cycle.";
            leaf XTURFECErrors {
              config false;
              description
              "Note: If the parameter is implemented but no
              value is  available, its value MUST be 4294967295
              (the maximum for its data type).";
              type uint32;
            }
            leaf XTUCFECErrors {
              config false;
              description
              "Note: If the parameter is implemented but no
              value is  available, its value MUST be 4294967295
              (the maximum for its data type).";
              type uint32;
            }
            leaf XTURHECErrors {
              config false;
              description
              "Note: If the parameter is implemented but no
              value is  available, its value MUST be 4294967295
              (the maximum for its data type).";
              type uint32;
            }
            leaf XTUCHECErrors {
              config false;
              description
              "Note: If the parameter is implemented but no
              value is  available, its value MUST be 4294967295
              (the maximum for its data type).";
              type uint32;
            }
            leaf XTURCRCErrors {
              config false;
              description
              "Note: If the parameter is implemented but no
              value is  available, its value MUST be 4294967295
              (the maximum for its data type).";
              type uint32;
            }
            leaf XTUCCRCErrors {
              config false;
              description
              "Note: If the parameter is implemented but no
              value is  available, its value MUST be 4294967295
              (the maximum for its data type).";
              type uint32;
            }
          }
          container LastShowtime {
            description
            "Note: The {{object}} parameters SHOULD NOT be reset
            when the interface statistics are reset via an
            interface disable / enable cycle.";
            leaf XTURFECErrors {
              config false;
              description
              "Note: If the parameter is implemented but no
              value is  available, its value MUST be 4294967295
              (the maximum for its data type).";
              type uint32;
            }
            leaf XTUCFECErrors {
              config false;
              description
              "Note: If the parameter is implemented but no
              value is  available, its value MUST be 4294967295
              (the maximum for its data type).";
              type uint32;
            }
            leaf XTURHECErrors {
              config false;
              description
              "Note: If the parameter is implemented but no
              value is  available, its value MUST be 4294967295
              (the maximum for its data type).";
              type uint32;
            }
            leaf XTUCHECErrors {
              config false;
              description
              "Note: If the parameter is implemented but no
              value is  available, its value MUST be 4294967295
              (the maximum for its data type).";
              type uint32;
            }
            leaf XTURCRCErrors {
              config false;
              description
              "Note: If the parameter is implemented but no
              value is  available, its value MUST be 4294967295
              (the maximum for its data type).";
              type uint32;
            }
            leaf XTUCCRCErrors {
              config false;
              description
              "Note: If the parameter is implemented but no
              value is  available, its value MUST be 4294967295
              (the maximum for its data type).";
              type uint32;
            }
          }
          container CurrentDay {
            description
            "Note: The {{object}} parameters SHOULD NOT be reset
            when the interface statistics are reset via an
            interface disable / enable cycle.";
            leaf XTURFECErrors {
              config false;
              description
              "Note: If the parameter is implemented but no
              value is  available, its value MUST be 4294967295
              (the maximum for its data type).";
              type uint32;
            }
            leaf XTUCFECErrors {
              config false;
              description
              "Note: If the parameter is implemented but no
              value is  available, its value MUST be 4294967295
              (the maximum for its data type).";
              type uint32;
            }
            leaf XTURHECErrors {
              config false;
              description
              "Note: If the parameter is implemented but no
              value is  available, its value MUST be 4294967295
              (the maximum for its data type).";
              type uint32;
            }
            leaf XTUCHECErrors {
              config false;
              description
              "Note: If the parameter is implemented but no
              value is  available, its value MUST be 4294967295
              (the maximum for its data type).";
              type uint32;
            }
            leaf XTURCRCErrors {
              config false;
              description
              "Note: If the parameter is implemented but no
              value is  available, its value MUST be 4294967295
              (the maximum for its data type).";
              type uint32;
            }
            leaf XTUCCRCErrors {
              config false;
              description
              "Note: If the parameter is implemented but no
              value is  available, its value MUST be 4294967295
              (the maximum for its data type).";
              type uint32;
            }
          }
          container QuarterHour {
            description
            "Note: The {{object}} parameters SHOULD NOT be reset
            when the interface statistics are reset via an
            interface disable / enable cycle.";
            leaf XTURFECErrors {
              config false;
              description
              "Note: If the parameter is implemented but no
              value is  available, its value MUST be 4294967295
              (the maximum for its data type).";
              type uint32;
            }
            leaf XTUCFECErrors {
              config false;
              description
              "Note: If the parameter is implemented but no
              value is  available, its value MUST be 4294967295
              (the maximum for its data type).";
              type uint32;
            }
            leaf XTURHECErrors {
              config false;
              description
              "Note: If the parameter is implemented but no
              value is  available, its value MUST be 4294967295
              (the maximum for its data type).";
              type uint32;
            }
            leaf XTUCHECErrors {
              config false;
              description
              "Note: If the parameter is implemented but no
              value is  available, its value MUST be 4294967295
              (the maximum for its data type).";
              type uint32;
            }
            leaf XTURCRCErrors {
              config false;
              description
              "Note: If the parameter is implemented but no
              value is  available, its value MUST be 4294967295
              (the maximum for its data type).";
              type uint32;
            }
            leaf XTUCCRCErrors {
              config false;
              description
              "Note: If the parameter is implemented but no
              value is  available, its value MUST be 4294967295
              (the maximum for its data type).";
              type uint32;
            }
          }
        }
      }
      list BondingGroup {
        key "GroupID";
        unique "Alias";
        unique "Name";
        config true;
        description
        "The DSL bonding data model is closely aligned with
        {{bibref|TR-159}}. Corresponds to {{bibref|TR-159}}
        ''oBondingGroup''.";
        leaf Enable {
          config true;
          description
          "This parameter is based on ''ifAdminStatus'' from
          {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config false;
          description
          "The textual name of the bonding group as assigned by
          the CPE.";
          type string {
            length "0..64";
          }
        }
        leaf LastChange {
          config false;
          description
          "The accumulated time in {{units}} since the bonding
          group entered its current operational state.";
          type uint32;
        }
        leaf-list LowerLayers {
          config false;
          description
          "{{param}} is read-only for this object because
          bonding is expected to be configured by the CPE, not
          by the ACS.";
          type string;
        }
        leaf-list GroupStatus {
          config false;
          description
          "Corresponds to {{bibref|TR-159}}
          ''oBondingGroup.aGroupStatus''.";
          type enumeration {
            enum "NoPeer" {
              description
              "Peer physical layer is unreachable";
            }
            enum "PeerPowerLoss" {
              description
              "Local device received a \"dying gasp\" message
              (preceding a loss-of-power) from the peer  device";
            }
            enum "PeerBondSchemeMismatch" {
              description
              "Operating bonding scheme of the peer port is
              different from the local one";
            }
            enum "LowRate" {
              description
              "Upstream or downstream data rate is at or below
              threshold";
            }
          }
        }
        leaf GroupID {
          config true;
          description
          "DSL bonding group ID.  Corresponds to
          {{bibref|TR-159}} ''oBondingGroup.aGroupID''.";
          type uint32;
        }
        leaf-list BondSchemesSupported {
          config false;
          description
          "Corresponds to {{bibref|TR-159}}
          ''oBondingGroup.aGroupBondSchemesSupported''.";
          type enumeration {
            enum "ATM" {
              description
              "{{bibref|G.998.1}} ATM-based bonding";
            }
            enum "Ethernet" {
              description
              "{{bibref|G.998.2}} Ethernet-based bonding";
            }
            enum "TDIM" {
              description
              "{{bibref|G.998.3}} TDIM-based bonding";
            }
          }
        }
        leaf BondScheme {
          config false;
          description
          "Currently operating bonding scheme.  Corresponds to
          {{bibref|TR-159}} ''aGroupOperBondScheme''.";
          type string;
          must ". = ../BondSchemesSupported";
        }
        leaf GroupCapacity {
          config false;
          description
          "DSL bonding group capacity, i.e.  the maximum number
          of channels that can be bonded in this group.
          Corresponds to  {{bibref|TR-159}}
          ''oBondingGroup.aGroupCapacity''.";
          type uint32 {
            range "1..32";
          }
        }
        leaf RunningTime {
          config false;
          description
          "The accumulated time in {{units}} for which this
          bonding group has been operationally up.  Corresponds
          to  {{bibref|G.998.1|section 11.4.2}} ''Group Running
          Time''.";
          type uint32;
        }
        leaf TargetUpRate {
          config false;
          description
          "Desired upstream data rate in {{units}} for this DSL
          bonding group (zero indicates best effort).
          Corresponds to  {{bibref|TR-159}}
          ''oBondingGroup.aGroupTargetUpRate''.";
          type uint32;
        }
        leaf TargetDownRate {
          config false;
          description
          "Desired downstream data rate in {{units}} for DSL
          bonding group (zero indicates best effort).
          Corresponds to  {{bibref|TR-159}}
          ''oBondingGroup.aGroupTargetDownRate''.";
          type uint32;
        }
        leaf ThreshLowUpRate {
          config false;
          description
          "Threshold upstream data rate in {{units}} for this
          DSL bonding group.  {{param|GroupStatus}} will
          include  {{enum|LowRate|GroupStatus}} whenever the
          upstream rate is less than this threshold.
          Corresponds to {{bibref|TR-159}}
          ''oBondingGroup.aGroupThreshLowUpRate''.";
          type uint32;
        }
        leaf ThreshLowDownRate {
          config false;
          description
          "Threshold downstream data rate in {{units}} for this
          DSL bonding group.  {{param|GroupStatus}} will
          include  {{enum|LowRate|GroupStatus}} whenever the
          downstream rate is less than this threshold.
          Corresponds to {{bibref|TR-159}}
          ''oBondingGroup.aGroupThreshLowDownRate''.";
          type uint32;
        }
        leaf UpstreamDifferentialDelayTolerance {
          config false;
          description
          "The maximum upstream differential delay in {{units}}
          among member links in a bonding group.  Corresponds
          to  {{bibref|G.998.1|section 11.4.1}} ''Differential
          Delay Tolerance''.";
          type uint32;
        }
        leaf DownstreamDifferentialDelayTolerance {
          config false;
          description
          "The maximum downstream differential delay in
          {{units}} among member links in a bonding group.
          Corresponds to  {{bibref|G.998.1|section 11.4.1}}
          ''Differential Delay Tolerance''.";
          type uint32;
        }
        leaf BondedChannelNumberOfEntries {
          config false;
          description
          "{{numentries}} Corresponds to {{bibref|TR-159}}
          ''oBondingGroup.aGroupNumChannels''.";
          type uint32 {
            range "1..32";
          }
        }
        list BondedChannel {
          key "Channel";
          unique "Alias";
          config true;
          description
          "When a {{object|.DSL.Channel}} or
          {{object|.FAST.Line}} is no longer bonded, then the
          CPE MUST delete the corresponding {{object}}
          instance.  However, when a bonded
          {{object|.DSL.Channel}} or {{object|.FAST.Line}}
          becomes disabled, the channel remains bonded and so
          the corresponding {{object}} instance MUST NOT be
          deleted.";
          leaf Alias {
            config true;
            description
            "{{datatype|expand}}";
            type Alias;
          }
          leaf Channel {
            config true;
            description
            "This is read-only because bonding is expected to be
            configured by the CPE, not by the ACS.";
            type string {
              length "0..256";
            }
          }
          container Ethernet {
            description
            "This object MUST be present if, and only if,
            {{param|##.BondScheme}} is
            {{enum|Ethernet|##.BondScheme}}.";
            container Stats {
              description
              "The CPE MUST reset the Stats parameters either
              when the interface becomes operationally down due
              to a previous administrative down (i.e.  the
              interface's {{param|###.Status}} parameter
              transitions to a down state after the interface
              is disabled) or when the interface becomes
              administratively up (i.e.  the interface's
              {{param|###.Enable}} parameter transitions from
              {{false}} to {{true}}). Administrative and
              operational interface status is discussed in
              {{bibref|TR-181i2|section 4.2.2}}.";
              leaf UnderflowErrorsSent {
                config false;
                description
                "Number of underflow errors sent, i.e.  on the
                transmit side of the interface.";
                type uint32;
              }
              leaf CRCErrorsReceived {
                config false;
                description
                "Number of CRC errors received, i.e.  on the
                receive side of the interface.";
                type uint32;
              }
              leaf AlignmentErrorsReceived {
                config false;
                description
                "Number of alignment errors received, i.e.  on
                the receive side of the interface.";
                type uint32;
              }
              leaf ShortPacketsReceived {
                config false;
                description
                "Number of short packets received, i.e.  on the
                receive side of the interface.";
                type uint32;
              }
              leaf LongPacketsReceived {
                config false;
                description
                "Number of long packets received, i.e.  on the
                receive side of the interface.";
                type uint32;
              }
              leaf OverflowErrorsReceived {
                config false;
                description
                "Number of overflow errors received, i.e.  on
                the receive side of the interface.";
                type uint32;
              }
              leaf PauseFramesReceived {
                config false;
                description
                "Number of pause frames received, i.e.  on the
                receive side of the interface.";
                type uint32;
              }
              leaf FramesDropped {
                config false;
                description
                "Number of frames dropped, e.g.  because the
                receive queue is full.";
                type uint32;
              }
            }
          }
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "The total number of packets that higher-level
            protocols requested for transmission and which were
            addressed to a broadcast address at this layer,
            including those that were discarded or not sent.";
            type uint64;
          }
          leaf BroadcastPacketsReceived {
            config false;
            description
            "The total number of received packets, delivered by
            this layer to a higher layer, which were addressed
            to a broadcast address at this layer.";
            type uint64;
          }
          leaf UnknownProtoPacketsReceived {
            config false;
            description
            "The total number of packets received via the
            interface which were discarded because of an
            unknown or unsupported  protocol.";
            type uint32;
          }
          leaf TotalStart {
            config false;
            description
            "Note: {{param}} SHOULD NOT be reset when the
            interface statistics are reset via an interface
            disable / enable cycle.";
            type uint32;
          }
          leaf CurrentDayStart {
            config false;
            description
            "Note: {{param}} SHOULD NOT be reset when the
            interface statistics are reset via an interface
            disable / enable cycle.";
            type uint32;
          }
          leaf QuarterHourStart {
            config false;
            description
            "Note: {{param}} SHOULD NOT be reset when the
            interface statistics are reset via an interface
            disable / enable cycle.";
            type uint32;
          }
          container Total {
            description
            "Note: The {{object}} parameters SHOULD NOT be reset
            when the interface statistics are reset via an
            interface disable / enable cycle.";
            leaf-list FailureReasons {
              config false;
              description
              "Corresponds to {{bibref|G.998.1|section 11.4.3}}
              ''Current Group Failure Reason''.";
              type enumeration {
                enum "LowRate" {
                  description
                  "Minimum data rate not met";
                }
                enum "ExcessiveDelay" {
                  description
                  "Differential delay tolerance exceeded";
                }
                enum "InsufficientBuffers" {
                  description
                  "Insufficient buffers on receiver";
                }
                enum "Other" {
                  description
                  "Other failure occurred";
                }
              }
            }
            leaf UpstreamRate {
              config false;
              description
              "The achieved upstream data rate in {{units}}
              (which might change subject to dynamic link usage
              conditions).  Corresponds to
              {{bibref|G.998.1|section 11.4.2}} ''Achieved
              Aggregate Data Rate''.";
              type uint32;
            }
            leaf DownstreamRate {
              config false;
              description
              "The achieved downstream data rate in {{units}}
              (which might change subject to dynamic link usage
              conditions).   Corresponds to
              {{bibref|G.998.1|section 11.4.2}} ''Achieved
              Aggregate Data Rate''.";
              type uint32;
            }
            leaf UpstreamPacketLoss {
              config false;
              description
              "The total number of upstream packets that were
              lost at aggregation output from a bonding group
              during the  accumulation period.  Corresponds to
              {{bibref|G.998.1|section 11.4.2}} ''Group Rx Cell
              Loss Count''.";
              type uint32;
            }
            leaf DownstreamPacketLoss {
              config false;
              description
              "The total number of downstream packets that were
              lost at aggregation output from a bonding group
              during the  accumulation period.  Corresponds to
              {{bibref|G.998.1|section 11.4.2}} ''Group Rx Cell
              Loss Count''.";
              type uint32;
            }
            leaf UpstreamDifferentialDelay {
              config false;
              description
              "The achieved upstream differential delay in
              {{units}} (which might change subject to dynamic
              link usage  conditions).";
              type uint32;
            }
            leaf DownstreamDifferentialDelay {
              config false;
              description
              "The achieved downstream differential delay in
              {{units}} (which might change subject to dynamic
              link usage  conditions).";
              type uint32;
            }
            leaf FailureCount {
              config false;
              description
              "The number of times that the group was declared
              ''Unavailable'' during the accumulation period.
              Corresponds to  {{bibref|G.998.1|Section 11.4.3}}
              ''Group Failure Count''.";
              type uint32;
            }
            leaf ErroredSeconds {
              config false;
              description
              "The time in {{units}} during which the group was
              declared ''Errored'' during the accumulation
              period.  Corresponds to {{bibref|TR-159}}
              ''oBondingGroup.aGroupPerf**ES''.";
              type uint32;
            }
            leaf SeverelyErroredSeconds {
              config false;
              description
              "The time in {{units}} during which the group was
              declared ''SeverelyErrored'' during the
              accumulation period.  Corresponds to
              {{bibref|TR-159}}
              ''oBondingGroup.aGroupPerf**SES''.";
              type uint32;
            }
            leaf UnavailableSeconds {
              config false;
              description
              "The time in {{units}} during which the group was
              declared ''Unavailable'' during the accumulation
              period.  Corresponds to {{bibref|TR-159}}
              ''oBondingGroup.aGroupPerf**UAS''.";
              type uint32;
            }
          }
          container CurrentDay {
            description
            "Note: The {{object}} parameters SHOULD NOT be reset
            when the interface statistics are reset via an
            interface disable / enable cycle.";
            leaf-list FailureReasons {
              config false;
              description
              "Corresponds to {{bibref|G.998.1|section 11.4.3}}
              ''Current Group Failure Reason''.";
              type enumeration {
                enum "LowRate" {
                  description
                  "Minimum data rate not met";
                }
                enum "ExcessiveDelay" {
                  description
                  "Differential delay tolerance exceeded";
                }
                enum "InsufficientBuffers" {
                  description
                  "Insufficient buffers on receiver";
                }
                enum "Other" {
                  description
                  "Other failure occurred";
                }
              }
            }
            leaf UpstreamRate {
              config false;
              description
              "The achieved upstream data rate in {{units}}
              (which might change subject to dynamic link usage
              conditions).  Corresponds to
              {{bibref|G.998.1|section 11.4.2}} ''Achieved
              Aggregate Data Rate''.";
              type uint32;
            }
            leaf DownstreamRate {
              config false;
              description
              "The achieved downstream data rate in {{units}}
              (which might change subject to dynamic link usage
              conditions).   Corresponds to
              {{bibref|G.998.1|section 11.4.2}} ''Achieved
              Aggregate Data Rate''.";
              type uint32;
            }
            leaf UpstreamPacketLoss {
              config false;
              description
              "The total number of upstream packets that were
              lost at aggregation output from a bonding group
              during the  accumulation period.  Corresponds to
              {{bibref|G.998.1|section 11.4.2}} ''Group Rx Cell
              Loss Count''.";
              type uint32;
            }
            leaf DownstreamPacketLoss {
              config false;
              description
              "The total number of downstream packets that were
              lost at aggregation output from a bonding group
              during the  accumulation period.  Corresponds to
              {{bibref|G.998.1|section 11.4.2}} ''Group Rx Cell
              Loss Count''.";
              type uint32;
            }
            leaf UpstreamDifferentialDelay {
              config false;
              description
              "The achieved upstream differential delay in
              {{units}} (which might change subject to dynamic
              link usage  conditions).";
              type uint32;
            }
            leaf DownstreamDifferentialDelay {
              config false;
              description
              "The achieved downstream differential delay in
              {{units}} (which might change subject to dynamic
              link usage  conditions).";
              type uint32;
            }
            leaf FailureCount {
              config false;
              description
              "The number of times that the group was declared
              ''Unavailable'' during the accumulation period.
              Corresponds to  {{bibref|G.998.1|Section 11.4.3}}
              ''Group Failure Count''.";
              type uint32;
            }
            leaf ErroredSeconds {
              config false;
              description
              "The time in {{units}} during which the group was
              declared ''Errored'' during the accumulation
              period.  Corresponds to {{bibref|TR-159}}
              ''oBondingGroup.aGroupPerf**ES''.";
              type uint32;
            }
            leaf SeverelyErroredSeconds {
              config false;
              description
              "The time in {{units}} during which the group was
              declared ''SeverelyErrored'' during the
              accumulation period.  Corresponds to
              {{bibref|TR-159}}
              ''oBondingGroup.aGroupPerf**SES''.";
              type uint32;
            }
            leaf UnavailableSeconds {
              config false;
              description
              "The time in {{units}} during which the group was
              declared ''Unavailable'' during the accumulation
              period.  Corresponds to {{bibref|TR-159}}
              ''oBondingGroup.aGroupPerf**UAS''.";
              type uint32;
            }
          }
          container QuarterHour {
            description
            "Note: The {{object}} parameters SHOULD NOT be reset
            when the interface statistics are reset via an
            interface disable / enable cycle.";
            leaf-list FailureReasons {
              config false;
              description
              "Corresponds to {{bibref|G.998.1|section 11.4.3}}
              ''Current Group Failure Reason''.";
              type enumeration {
                enum "LowRate" {
                  description
                  "Minimum data rate not met";
                }
                enum "ExcessiveDelay" {
                  description
                  "Differential delay tolerance exceeded";
                }
                enum "InsufficientBuffers" {
                  description
                  "Insufficient buffers on receiver";
                }
                enum "Other" {
                  description
                  "Other failure occurred";
                }
              }
            }
            leaf UpstreamRate {
              config false;
              description
              "The achieved upstream data rate in {{units}}
              (which might change subject to dynamic link usage
              conditions).  Corresponds to
              {{bibref|G.998.1|section 11.4.2}} ''Achieved
              Aggregate Data Rate''.";
              type uint32;
            }
            leaf DownstreamRate {
              config false;
              description
              "The achieved downstream data rate in {{units}}
              (which might change subject to dynamic link usage
              conditions).   Corresponds to
              {{bibref|G.998.1|section 11.4.2}} ''Achieved
              Aggregate Data Rate''.";
              type uint32;
            }
            leaf UpstreamPacketLoss {
              config false;
              description
              "The total number of upstream packets that were
              lost at aggregation output from a bonding group
              during the  accumulation period.  Corresponds to
              {{bibref|G.998.1|section 11.4.2}} ''Group Rx Cell
              Loss Count''.";
              type uint32;
            }
            leaf DownstreamPacketLoss {
              config false;
              description
              "The total number of downstream packets that were
              lost at aggregation output from a bonding group
              during the  accumulation period.  Corresponds to
              {{bibref|G.998.1|section 11.4.2}} ''Group Rx Cell
              Loss Count''.";
              type uint32;
            }
            leaf UpstreamDifferentialDelay {
              config false;
              description
              "The achieved upstream differential delay in
              {{units}} (which might change subject to dynamic
              link usage  conditions).";
              type uint32;
            }
            leaf DownstreamDifferentialDelay {
              config false;
              description
              "The achieved downstream differential delay in
              {{units}} (which might change subject to dynamic
              link usage  conditions).";
              type uint32;
            }
            leaf FailureCount {
              config false;
              description
              "The number of times that the group was declared
              ''Unavailable'' during the accumulation period.
              Corresponds to  {{bibref|G.998.1|Section 11.4.3}}
              ''Group Failure Count''.";
              type uint32;
            }
            leaf ErroredSeconds {
              config false;
              description
              "The time in {{units}} during which the group was
              declared ''Errored'' during the accumulation
              period.  Corresponds to {{bibref|TR-159}}
              ''oBondingGroup.aGroupPerf**ES''.";
              type uint32;
            }
            leaf SeverelyErroredSeconds {
              config false;
              description
              "The time in {{units}} during which the group was
              declared ''SeverelyErrored'' during the
              accumulation period.  Corresponds to
              {{bibref|TR-159}}
              ''oBondingGroup.aGroupPerf**SES''.";
              type uint32;
            }
            leaf UnavailableSeconds {
              config false;
              description
              "The time in {{units}} during which the group was
              declared ''Unavailable'' during the accumulation
              period.  Corresponds to {{bibref|TR-159}}
              ''oBondingGroup.aGroupPerf**UAS''.";
              type uint32;
            }
          }
        }
        container Ethernet {
          description
          "This object MUST be present if, and only if,
          {{param|#.BondScheme}} is
          {{enum|Ethernet|#.BondScheme}}.";
          container Stats {
            description
            "The CPE MUST reset the Stats parameters either when
            the interface becomes operationally down due to a
            previous administrative down (i.e.  the interface's
            {{param|##.Status}} parameter transitions to a down
            state after the interface is disabled) or when the
            interface becomes administratively up (i.e.  the
            interface's {{param|##.Enable}} parameter
            transitions from {{false}} to {{true}}).
            Administrative and operational interface status is
            discussed in {{bibref|TR-181i2|section 4.2.2}}.";
            leaf PAFErrors {
              config false;
              description
              "Number of PAF errors.  Corresponds to
              {{bibref|TR-159}} ''oBondETH.aEthRxErrors''.";
              type uint32;
            }
            leaf PAFSmallFragments {
              config false;
              description
              "Number of PAF Small Fragment events.  Corresponds
              to {{bibref|TR-159}}
              ''oBondETH.aEthRxSmallFragments''.";
              type uint32;
            }
            leaf PAFLargeFragments {
              config false;
              description
              "Number of PAF Large Fragment events.  Corresponds
              to {{bibref|TR-159}}
              ''oBondETH.aEthRxLargeFragments''.";
              type uint32;
            }
            leaf PAFBadFragments {
              config false;
              description
              "Number of PAF Bad Fragment events.  Corresponds
              to {{bibref|TR-159}}
              ''oBondETH.aEthRxBadFragments''.";
              type uint32;
            }
            leaf PAFLostFragments {
              config false;
              description
              "Number of PAF Lost Fragment events.  Corresponds
              to {{bibref|TR-159}}
              ''oBondETH.aEthRxLostFragments''.";
              type uint32;
            }
            leaf PAFLateFragments {
              config false;
              description
              "Number of PAF Late Fragment events.";
              type uint32;
            }
            leaf PAFLostStarts {
              config false;
              description
              "Number of PAF Lost Start events.  Corresponds to
              {{bibref|TR-159}} ''oBondETH.aEthRxLostStarts''.";
              type uint32;
            }
            leaf PAFLostEnds {
              config false;
              description
              "Number of PAF Lost End events.  Corresponds to
              {{bibref|TR-159}} ''oBondETH.aEthRxLostEnds''.";
              type uint32;
            }
            leaf PAFOverflows {
              config false;
              description
              "Number of PAF Overflow events.  Corresponds to
              {{bibref|TR-159}} ''oBondETH.aEthRxOverflows''.";
              type uint32;
            }
            leaf PauseFramesSent {
              config false;
              description
              "Number of pause frames sent, i.e.  on the
              transmit side of the interface.";
              type uint32;
            }
            leaf CRCErrorsReceived {
              config false;
              description
              "Number of CRC errors received, i.e.  on the
              receive side of the interface.";
              type uint32;
            }
            leaf AlignmentErrorsReceived {
              config false;
              description
              "Number of alignment errors received, i.e.  on the
              receive side of the interface.";
              type uint32;
            }
            leaf ShortPacketsReceived {
              config false;
              description
              "Number of short packets received, i.e.  on the
              receive side of the interface.";
              type uint32;
            }
            leaf LongPacketsReceived {
              config false;
              description
              "Number of long packets received, i.e.  on the
              receive side of the interface.";
              type uint32;
            }
            leaf OverflowErrorsReceived {
              config false;
              description
              "Number of overflow errors received, i.e.  on the
              receive side of the interface.";
              type uint32;
            }
            leaf FramesDropped {
              config false;
              description
              "Number of frames dropped, e.g.  because the
              receive queue is full.";
              type uint32;
            }
          }
        }
      }
      container Diagnostics {
        description
        "The DSL Diagnostics object.";
        container ADSLLineTest {
          description
          "This object is to provide diagnostic information for
          a CPE with an ADSL2 or ADSL2+ modem WAN interface,
          but MAY also be used for ADSL.";
          leaf DiagnosticsState {
            config true;
            description
            "{{datatype|expand}}";
            type DiagnosticsState;
          }
          leaf Interface {
            config true;
            description
            "{{reference}}  This is the interface over which the
            test is to be performed.";
            type string {
              length "0..256";
            }
          }
          leaf ACTPSDds {
            config false;
            description
            "Note:  See ITU-T Recommendation {{bibref|G.997.1}}.";
            type int32;
          }
          leaf ACTPSDus {
            config false;
            description
            "Note:  See ITU-T Recommendation {{bibref|G.997.1}}.";
            type int32;
          }
          leaf ACTATPds {
            config false;
            description
            "Note:  See ITU-T Recommendation {{bibref|G.997.1}}.";
            type int32;
          }
          leaf ACTATPus {
            config false;
            description
            "Note:  See ITU-T Recommendation {{bibref|G.997.1}}.";
            type int32;
          }
          leaf HLINSCds {
            config false;
            description
            "Note:  See ITU-T Recommendation {{bibref|G.997.1}}.
            For a multimode device operating in a mode in which
            this parameter does not apply, the value  of this
            parameter SHOULD be set to 0.";
            type int32;
          }
          leaf HLINSCus {
            config false;
            description
            "Note:  See ITU-T Recommendation {{bibref|G.997.1}}.
            For a multimode device operating in a mode in which
            this parameter does not apply, the value  of this
            parameter SHOULD be set to 0.";
            type int32;
          }
          leaf HLINGds {
            config false;
            description
            "Note:  See ITU-T Recommendation {{bibref|G.997.1}}.
            For a multimode device operating in a mode in which
            this parameter does not apply, the value  of this
            parameter SHOULD be set to 1.";
            type uint32;
          }
          leaf HLINGus {
            config false;
            description
            "Note:  See ITU-T Recommendation {{bibref|G.997.1}}.
            For a multimode device operating in a mode in which
            this parameter does not apply, the value  of this
            parameter SHOULD be set to 1.";
            type uint32;
          }
          leaf HLOGGds {
            config false;
            description
            "Note:  See ITU-T Recommendation {{bibref|G.997.1}}.
            For a multimode device operating in a mode in which
            this parameter does not apply, the value  of this
            parameter SHOULD be set to 1.";
            type uint32;
          }
          leaf HLOGGus {
            config false;
            description
            "Note:  See ITU-T Recommendation {{bibref|G.997.1}}.
            For a multimode device operating in a mode in which
            this parameter does not apply, the value  of this
            parameter SHOULD be set to 1.";
            type uint32;
          }
          leaf-list HLOGpsds {
            config false;
            description
            "Note: {{param}} is measured during initialization
            and is not updated during Showtime.";
            type string;
          }
          leaf-list HLOGpsus {
            config false;
            description
            "Note: {{param}} is measured during initialization
            and is not updated during Showtime.";
            type string;
          }
          leaf HLOGMTds {
            config false;
            description
            "Note:  See ITU-T Recommendation {{bibref|G.997.1}}.
            For a multimode device operating in a mode in which
            this parameter does not apply, the value  of this
            parameter SHOULD be set to 0.";
            type uint32;
          }
          leaf HLOGMTus {
            config false;
            description
            "Note:  See ITU-T Recommendation {{bibref|G.997.1}}.
            For a multimode device operating in a mode in which
            this parameter does not apply, the value  of this
            parameter SHOULD be set to 0.";
            type uint32;
          }
          leaf-list LATNpbds {
            config false;
            description
            "Note:  See ITU-T Recommendation {{bibref|G.997.1}}.";
            type string;
          }
          leaf-list LATNpbus {
            config false;
            description
            "Note:  See ITU-T Recommendation {{bibref|G.997.1}}.";
            type string;
          }
          leaf-list SATNds {
            config false;
            description
            "Note:  See ITU-T Recommendation {{bibref|G.997.1}}.";
            type string;
          }
          leaf-list SATNus {
            config false;
            description
            "Note:  See ITU-T Recommendation {{bibref|G.997.1}}.";
            type string;
          }
          leaf-list HLINpsds {
            config false;
            description
            "Note:  See ITU-T Recommendation {{bibref|G.997.1}}.
            For a multimode device operating in a mode in which
            this parameter does not apply, the value  of this
            parameter SHOULD be set to ''None''.";
            type int32;
          }
          leaf-list HLINpsus {
            config false;
            description
            "Note:  See ITU-T Recommendation {{bibref|G.997.1}}.
            For a multimode device operating in a mode in which
            this parameter does not apply, the value  of this
            parameter SHOULD be set to ''None''.";
            type string;
          }
          leaf QLNGds {
            config false;
            description
            "Note:  See ITU-T Recommendation {{bibref|G.997.1}}.
            For a multimode device operating in a mode in which
            this parameter does not apply, the value  of this
            parameter SHOULD be set to 1.";
            type uint32;
          }
          leaf QLNGus {
            config false;
            description
            "Note:  See ITU-T Recommendation {{bibref|G.997.1}}.
            For a multimode device operating in a mode in which
            this parameter does not apply, the value  of this
            parameter SHOULD be set to 1.";
            type uint32;
          }
          leaf-list QLNpsds {
            config false;
            description
            "Note:  See ITU-T Recommendation {{bibref|G.997.1}}.
            For a multimode device operating in a mode in which
            this parameter does not apply, the value  of this
            parameter SHOULD be set to ''None''.";
            type int32;
          }
          leaf-list QLNpsus {
            config false;
            description
            "Note:  See ITU-T Recommendation {{bibref|G.997.1}}.
            For a multimode device operating in a mode in which
            this parameter does not apply, the value  of this
            parameter SHOULD be set to ''None''.";
            type string;
          }
          leaf QLNMTds {
            config false;
            description
            "Note:  See ITU-T Recommendation {{bibref|G.997.1}}.
            For a multimode device operating in a mode in which
            this parameter does not apply, the value  of this
            parameter SHOULD be set to 0.";
            type uint32;
          }
          leaf QLNMTus {
            config false;
            description
            "Note:  See ITU-T Recommendation {{bibref|G.997.1}}.
            For a multimode device operating in a mode in which
            this parameter does not apply, the value  of this
            parameter SHOULD be set to 0.";
            type uint32;
          }
          leaf SNRGds {
            config false;
            description
            "Note:  See ITU-T Recommendation {{bibref|G.997.1}}.
            For a multimode device operating in a mode in which
            this parameter does not apply, the value  of this
            parameter SHOULD be set to 1.";
            type uint32;
          }
          leaf SNRGus {
            config false;
            description
            "Note:  See ITU-T Recommendation {{bibref|G.997.1}}.
            For a multimode device operating in a mode in which
            this parameter does not apply, the value  of this
            parameter SHOULD be set to 1.";
            type uint32;
          }
          leaf-list SNRpsds {
            config false;
            description
            "Note:  See ITU-T Recommendation {{bibref|G.997.1}}.
            For a multimode device operating in a mode in which
            this parameter does not apply, the value  of this
            parameter SHOULD be set to ''None''.";
            type int32;
          }
          leaf-list SNRpsus {
            config false;
            description
            "Note:  See ITU-T Recommendation {{bibref|G.997.1}}.
            For a multimode device operating in a mode in which
            this parameter does not apply, the value  of this
            parameter SHOULD be set to ''None''.";
            type string;
          }
          leaf SNRMTds {
            config false;
            description
            "Note:  See ITU-T Recommendation {{bibref|G.997.1}}.
            For a multimode device operating in a mode in which
            this parameter does not apply, the value  of this
            parameter SHOULD be set to 0.";
            type uint32;
          }
          leaf SNRMTus {
            config false;
            description
            "Note:  See ITU-T Recommendation {{bibref|G.997.1}}.
            For a multimode device operating in a mode in which
            this parameter does not apply, the value  of this
            parameter SHOULD be set to 0.";
            type uint32;
          }
          leaf-list BITSpsds {
            config false;
            description
            "{{list}} List items represent downstream bit
            allocation per subcarrier group.  Maximum number of
            elements is 256 for G.992.3, 512 for G.992.5.
            Interpretation of the value is as defined in ITU-T
            Rec.  {{bibref|G.997.1}}.";
            type int32;
          }
          leaf-list BITSpsus {
            config false;
            description
            "{{list}} List items represent upstream bit
            allocation per subcarrier group.  Maximum number of
            elements is 256 for G.992.3, 512 for G.992.5.
            Interpretation of the value is as defined in ITU-T
            Rec.  {{bibref|G.997.1}}.";
            type string;
          }
        }
      }
    }
    container FAST {
      description
      "This object models FAST (defined in ITU Recommendation
      {{bibref|G.9701}}) lines.  Each {{object|Line}} models a
      layer 1 FAST Line interface.";
      leaf LineNumberOfEntries {
        config false;
        description
        "{{numentries}}";
        type uint32;
      }
      list Line {
        key "Name";
        unique "Alias";
        config true;
        description
        "This table models physical FAST lines.";
        leaf Enable {
          config true;
          description
          "Enables or disables the FAST line.  This parameter is
          based on ''ifAdminStatus'' from {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config true;
          description
          "The textual name of the FAST line as assigned by the
          CPE.";
          type string {
            length "0..64";
          }
        }
        leaf LastChange {
          config false;
          description
          "The accumulated time in {{units}} since the FAST line
          entered its current operational state.";
          type uint32;
        }
        leaf-list LowerLayers {
          config true;
          description
          "Note: Since {{object}} is a layer 1 interface, it is
          expected that {{param}} will not be used.";
          type string;
        }
        leaf Upstream {
          config false;
          description
          "* For an End Device, {{param}} will be {{true}} for
          all interfaces.";
          type boolean;
        }
        leaf FirmwareVersion {
          config false;
          description
          "A string identifying the version of the modem
          firmware currently installed for this interface.
          This is applicable only when the modem firmware is
          separable from the overall CPE software.";
          type string {
            length "0..64";
          }
        }
        leaf LinkStatus {
          config false;
          description
          "The {{enum|Error}} value MAY be used by the CPE to
          indicate a locally defined error condition.";
          type enumeration {
            enum "Up";
            enum "Initializing";
            enum "EstablishingLink";
            enum "NoSignal";
            enum "Disabled";
            enum "Error";
          }
        }
        leaf-list AllowedProfiles {
          config false;
          description
          "Note:  In G.997.2, this parameter is called PROFILES.
          See ITU-T Recommendation {{bibref|G.997.2}}.";
          type enumeration {
            enum "106a";
            enum "212a";
          }
        }
        leaf CurrentProfile {
          config false;
          description
          "Indicates which FAST profile is currently in use on
          the line.";
          type string;
          must ". = ../AllowedProfiles";
        }
        leaf PowerManagementState {
          config false;
          description
          "Note: See ITU-T Recommendation {{bibref|G.9701}}.";
          type enumeration {
            enum "L0";
            enum "L2.1";
            enum "L2.2";
            enum "L3";
          }
        }
        leaf SuccessFailureCause {
          config false;
          description
          "Recommendation {{bibref|G.997.2}}.";
          type uint32 {
            range "0..5";
          }
        }
        leaf UPBOKLER {
          config false;
          description
          "Note: This parameter is defined as UPBOKLE-R in
          Clause 7.10.4.2 of ITU-T Recommendation
          {{bibref|G.997.2}}.";
          type uint32 {
            range "0..1280";
          }
        }
        leaf LastTransmittedDownstreamSignal {
          config false;
          description
          "Note: See clause 7.10.2.2 ITU-T Recommendation
          {{bibref|G.997.2}}.";
          type uint32 {
            range "0..21";
          }
        }
        leaf LastTransmittedUpstreamSignal {
          config false;
          description
          "Note: See clause 7.10.2.3 ITU-T Recommendation
          {{bibref|G.997.2}}.";
          type uint32 {
            range "0..21";
          }
        }
        leaf UPBOKLE {
          config false;
          description
          "Note: See clause 7.10.4.1 in ITU-T Recommendation
          {{bibref|G.997.2}}.";
          type uint32 {
            range "0..1280";
          }
        }
        leaf LineNumber {
          config false;
          description
          "Signifies the line pair that the modem is using to
          connection.  {{param}} = 1 is the innermost  pair.";
          type int32 {
            range "1..max";
          }
        }
        leaf UpstreamMaxBitRate {
          config false;
          description
          "Note: This parameter is related to the G.997.2
          parameter ATTNDRus.  See clause 7.11.2.1 ITU-T
          Recommendation {{bibref|G.997.2}}.";
          type uint32;
        }
        leaf DownstreamMaxBitRate {
          config false;
          description
          "Note: This parameter is related to the G.997.2
          parameter ATTNDRds.  See clause 7.11.2.1 ITU-T
          Recommendation {{bibref|G.997.2}}.";
          type uint32;
        }
        leaf UpstreamNoiseMargin {
          config false;
          description
          "Note: In G.997.2, this parameter is called SNRMus.
          See ITU-T Recommendation {{bibref|G.997.2}}.";
          type int32;
        }
        leaf DownstreamNoiseMargin {
          config false;
          description
          "Note: In G.997.2, this parameter is called SNRMds.
          See ITU-T Recommendation {{bibref|G.997.2}}.";
          type int32;
        }
        leaf UpstreamAttenuation {
          config false;
          description
          "The current upstream signal loss (expressed in
          {{units}}).";
          type int32;
        }
        leaf DownstreamAttenuation {
          config false;
          description
          "The current downstream signal loss (expressed in
          {{units}}).";
          type int32;
        }
        leaf UpstreamPower {
          config false;
          description
          "The current output power at the CPE's FAST line
          (expressed in {{units}}).";
          type int32;
        }
        leaf DownstreamPower {
          config false;
          description
          "The current received power at the CPE's FAST line
          (expressed in {{units}}).";
          type int32;
        }
        leaf SNRMRMCds {
          config false;
          description
          "This parameter reports the signal-to-noise margin for
          the robust management channel (RMC) in the downstream
          direction (express in {{units}}). A special value
          (-512)  indicates that the signal-to-noise ratio
          margin for the RMC is out of the range to be
          represented.  This parameter is defined in clauses
          7.10.12.1 of ITU-T Recommendation {{bibref|G.997.2}}.";
          type int32;
        }
        leaf SNRMRMCus {
          config false;
          description
          "This parameter reports the signal-to-noise margin for
          the robust management channel (RMC) in the upstream
          direction (express in {{units}}). A special value
          (-512)  indicates that the signal-to-noise ratio
          margin for the RMC is out of the range to be
          represented.  This parameter is defined in clauses
          7.10.12.2 of ITU-T Recommendation {{bibref|G.997.2}}.";
          type int32;
        }
        leaf-list BITSRMCpsds {
          config false;
          description
          "{{list}} List items report the bit allocation values
          on RMC sub-carriers in RMC symbols in the downstream
          direction.  Each pair composes of a sub-carrier index
          from 0..4095 and an 8 bit allocation value.  There
          are maximum 512 pairs.  This parameter is defined in
          clause 7.10.12.3 of ITU-T Recommendation
          {{bibref|G.997.2}}.";
          type int32;
        }
        leaf-list BITSRMCpsus {
          config false;
          description
          "{{list}} List items report the bit allocation values
          on RMC sub-carriers in RMC symbols in the upstream
          direction.  Each pair composes of a sub-carrier index
          from 0..4095 and an 8 bit allocation value.  There
          are maximum 512 pairs.  This parameter is defined in
          clause 7.10.12.4 of ITU-T Recommendation
          {{bibref|G.997.2}}.";
          type int32;
        }
        leaf FEXTCANCELds {
          config false;
          description
          "This indicates whether FEXT cancellation in the
          downstream direction from all the other vectored
          lines into the line in the vectored group is enabled
          (TRUE) or disabled (FALSE). This parameter is defined
          as FEXT_TO_CANCEL_ENABLEds in clause 7.1.7.1 of ITU
          Recommendation {{bibref|G.997.2}}.";
          type boolean;
        }
        leaf FEXTCANCELus {
          config false;
          description
          "This indicates whether FEXT cancellation in the
          upstream direction from all the other vectored lines
          into the line in the vectored group is enabled (TRUE)
          or disabled (FALSE). This parameter is defined as
          FEXT_TO_CANCEL_ENABLEds in clause 7.1.7.1 of ITU
          Recommendation {{bibref|G.997.2}}.";
          type boolean;
        }
        leaf ETRds {
          config false;
          description
          "This parameter reports the expected throughput rate
          expressed in {{units}} as defined in clause 7.11.1.2
          of ITU-T Recommendation {{bibref|G.997.2}}";
          type uint32;
        }
        leaf ETRus {
          config false;
          description
          "This parameter reports the expected throughput rate
          expressed in {{units}} as defined in clause 7.11.1.2
          of ITU-T Recommendation {{bibref|G.997.2}}";
          type uint32;
        }
        leaf ATTETRds {
          config false;
          description
          "This parameter reports the attainable expected
          throughput expressed in {{units}} as defined in
          clause 7.11.2.2 of ITU-T Recommendation
          {{bibref|G.997.2}}";
          type uint32;
        }
        leaf ATTETRus {
          config false;
          description
          "This parameter reports the attainable expected
          throughput expressed in {{units}} as defined in
          clause 7.11.2.2 of ITU-T Recommendation
          {{bibref|G.997.2}}";
          type uint32;
        }
        leaf MINEFTR {
          config false;
          description
          "This parameter reports the minimum error free
          throughput value expressed in {{units}} computed from
          power up as defined in clause 11.4.1.1.3 of ITU-T
          Recommendation {{bibref|G.9701}}";
          type uint32;
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to prevent their being delivered.
            One possible reason for discarding such a packet
            could be to free up buffer space.";
            type uint32;
          }
          leaf TotalStart {
            config false;
            description
            "Note: {{param}} SHOULD NOT be reset when the
            interface statistics are reset via an interface
            disable / enable cycle.";
            type uint32;
          }
          leaf ShowtimeStart {
            config false;
            description
            "Note: {{param}} SHOULD NOT be reset when the
            interface statistics are reset via an interface
            disable / enable cycle.";
            type uint32;
          }
          leaf LastShowtimeStart {
            config false;
            description
            "Note: {{param}} SHOULD NOT be reset when the
            interface statistics are reset via an interface
            disable / enable cycle.";
            type uint32;
          }
          leaf CurrentDayStart {
            config false;
            description
            "Note: {{param}} SHOULD NOT be reset when the
            interface statistics are reset via an interface
            disable / enable cycle.";
            type uint32;
          }
          leaf QuarterHourStart {
            config false;
            description
            "Note: {{param}} SHOULD NOT be reset when the
            interface statistics are reset via an interface
            disable / enable cycle.";
            type uint32;
          }
          container Total {
            description
            "Note: The {{object}} parameters SHOULD NOT be reset
            when the interface statistics are reset via an
            interface disable / enable cycle.";
            leaf ErroredSecs {
              config false;
              description
              "Total number of errored seconds as defined in
              ITU-T Rec.  {{bibref|G.997.2}}. An errored second
              (ES) is declared if, during a 1-second interval,
              there are one or more crc anomalies, or one or
              more los defects, or one or more lor defects, or
              one or more lpr primitives.";
              type uint32;
            }
            leaf SeverelyErroredSecs {
              config false;
              description
              "Total number of severely errored seconds as
              defined in ITU-T Rec.  {{bibref|G.997.2}}.";
              type uint32;
            }
            leaf LOSS {
              config false;
              description
              "Total number of loss of signal seconds (LOSS) as
              defined in ITU-T Rec.  {{bibref|G.997.2}}. A LOSS
              is declared if, during a 1-second interval, there
              are one or more los defects.";
              type uint32;
            }
            leaf LORS {
              config false;
              description
              "Total number of loss of RMC seconds (LORS) as
              defined in ITU-T Rec.  {{bibref|G.997.2}}. A LORS
              is declared if, during a 1-second interval, there
              are one or more lor defects.";
              type uint32;
            }
            leaf UAS {
              config false;
              description
              "Total number of unavailable seconds (UAS) as
              defined in ITU-T Rec.  {{bibref|G.997.2}}.";
              type uint32;
            }
            leaf RTXUC {
              config false;
              description
              "This parameter reports a count of uncorrected DTU
              anomalies (rtx_uc). This parameter is defined in
              clause 7.8.5 of ITU-T Rec.  {{bibref|G.997.2}}.";
              type uint32;
            }
            leaf RTXTX {
              config false;
              description
              "This parameter reports a count of retransmitted
              DTU anomalies (rtx_tx). This parameter is defined
              in clause 7.8.6 of ITU-T Rec.
              {{bibref|G.997.2}}.";
              type uint32;
            }
            leaf SuccessBSW {
              config false;
              description
              "This parameter reports a count of the successful
              bit swap (BSW) primitives.  This parameter is
              defined as success_BSW in clause 7.7.20 of  ITU-T
              Rec.  {{bibref|G.997.2}}.";
              type uint32;
            }
            leaf SuccessSRA {
              config false;
              description
              "This parameter reports a count of the successful
              autonomous SRA (seamless rate adaptation)
              primitives.  This parameter is defined as
              success_SRA in clause 7.7.21 of  ITU-T Rec.
              {{bibref|G.997.2}}.";
              type uint32;
            }
            leaf SuccessFRA {
              config false;
              description
              "This parameter reports a count of the successful
              FRA (fast rate adaptation)  primitives.  This
              parameter is defined as success_FRA in clause
              7.7.22 of  ITU-T Rec.  {{bibref|G.997.2}}.";
              type uint32;
            }
            leaf SuccessRPA {
              config false;
              description
              "This parameter reports a count of the successful
              RPA (RMC parameter adjustment)  primitives.  This
              parameter is defined as success_RPA in clause
              7.7.23 of  ITU-T Rec.  {{bibref|G.997.2}}.";
              type uint32;
            }
            leaf SuccessTIGA {
              config false;
              description
              "This parameter reports a count of the successful
              TIGA (transmitter initiated gain adjustment)
              primitives.  This parameter is defined as
              success_TIGA in clause 7.7.24 of  ITU-T Rec.
              {{bibref|G.997.2}}.";
              type uint32;
            }
          }
          container Showtime {
            description
            "Note: The Total parameters SHOULD NOT be reset when
            the interface statistics are reset via an interface
            disable / enable cycle.";
            leaf ErroredSecs {
              config false;
              description
              "Total number of errored seconds as defined in
              ITU-T Rec.  {{bibref|G.997.2}}. An errored second
              (ES) is declared if, during a 1-second interval,
              there are one or more crc anomalies, or one or
              more los defects, or one or more lor defects, or
              one or more lpr primitives.";
              type uint32;
            }
            leaf SeverelyErroredSecs {
              config false;
              description
              "Total number of severely errored seconds as
              defined in ITU-T Rec.  {{bibref|G.997.2}}.";
              type uint32;
            }
            leaf LOSS {
              config false;
              description
              "Total number of loss of signal seconds (LOSS) as
              defined in ITU-T Rec.  {{bibref|G.997.2}}. A LOSS
              is declared if, during a 1-second interval, there
              are one or more los defects.";
              type uint32;
            }
            leaf LORS {
              config false;
              description
              "Total number of loss of RMC seconds (LORS) as
              defined in ITU-T Rec.  {{bibref|G.997.2}}. A LORS
              is declared if, during a 1-second interval, there
              are one or more lor defects.";
              type uint32;
            }
            leaf UAS {
              config false;
              description
              "Total number of unavailable seconds (UAS) as
              defined in ITU-T Rec.  {{bibref|G.997.2}}.";
              type uint32;
            }
            leaf RTXUC {
              config false;
              description
              "This parameter reports a count of uncorrected DTU
              anomalies (rtx_uc). This parameter is defined in
              clause 7.8.5 of ITU-T Rec.  {{bibref|G.997.2}}.";
              type uint32;
            }
            leaf RTXTX {
              config false;
              description
              "This parameter reports a count of retransmitted
              DTU anomalies (rtx_tx). This parameter is defined
              in clause 7.8.6 of ITU-T Rec.
              {{bibref|G.997.2}}.";
              type uint32;
            }
            leaf SuccessBSW {
              config false;
              description
              "This parameter reports a count of the successful
              bit swap (BSW) primitives.  This parameter is
              defined as success_BSW in clause 7.7.20 of  ITU-T
              Rec.  {{bibref|G.997.2}}.";
              type uint32;
            }
            leaf SuccessSRA {
              config false;
              description
              "This parameter reports a count of the successful
              autonomous SRA (seamless rate adaptation)
              primitives.  This parameter is defined as
              success_SRA in clause 7.7.21 of  ITU-T Rec.
              {{bibref|G.997.2}}.";
              type uint32;
            }
            leaf SuccessFRA {
              config false;
              description
              "This parameter reports a count of the successful
              FRA (fast rate adaptation)  primitives.  This
              parameter is defined as success_FRA in clause
              7.7.22 of  ITU-T Rec.  {{bibref|G.997.2}}.";
              type uint32;
            }
            leaf SuccessRPA {
              config false;
              description
              "This parameter reports a count of the successful
              RPA (RMC parameter adjustment)  primitives.  This
              parameter is defined as success_RPA in clause
              7.7.23 of  ITU-T Rec.  {{bibref|G.997.2}}.";
              type uint32;
            }
            leaf SuccessTIGA {
              config false;
              description
              "This parameter reports a count of the successful
              TIGA (transmitter initiated gain adjustment)
              primitives.  This parameter is defined as
              success_TIGA in clause 7.7.24 of  ITU-T Rec.
              {{bibref|G.997.2}}.";
              type uint32;
            }
          }
          container LastShowtime {
            description
            "Note: The Total parameters SHOULD NOT be reset when
            the interface statistics are reset via an interface
            disable / enable cycle.";
            leaf ErroredSecs {
              config false;
              description
              "Total number of errored seconds as defined in
              ITU-T Rec.  {{bibref|G.997.2}}. An errored second
              (ES) is declared if, during a 1-second interval,
              there are one or more crc anomalies, or one or
              more los defects, or one or more lor defects, or
              one or more lpr primitives.";
              type uint32;
            }
            leaf SeverelyErroredSecs {
              config false;
              description
              "Total number of severely errored seconds as
              defined in ITU-T Rec.  {{bibref|G.997.2}}.";
              type uint32;
            }
            leaf LOSS {
              config false;
              description
              "Total number of loss of signal seconds (LOSS) as
              defined in ITU-T Rec.  {{bibref|G.997.2}}. A LOSS
              is declared if, during a 1-second interval, there
              are one or more los defects.";
              type uint32;
            }
            leaf LORS {
              config false;
              description
              "Total number of loss of RMC seconds (LORS) as
              defined in ITU-T Rec.  {{bibref|G.997.2}}. A LORS
              is declared if, during a 1-second interval, there
              are one or more lor defects.";
              type uint32;
            }
            leaf UAS {
              config false;
              description
              "Total number of unavailable seconds (UAS) as
              defined in ITU-T Rec.  {{bibref|G.997.2}}.";
              type uint32;
            }
            leaf RTXUC {
              config false;
              description
              "This parameter reports a count of uncorrected DTU
              anomalies (rtx_uc). This parameter is defined in
              clause 7.8.5 of ITU-T Rec.  {{bibref|G.997.2}}.";
              type uint32;
            }
            leaf RTXTX {
              config false;
              description
              "This parameter reports a count of retransmitted
              DTU anomalies (rtx_tx). This parameter is defined
              in clause 7.8.6 of ITU-T Rec.
              {{bibref|G.997.2}}.";
              type uint32;
            }
            leaf SuccessBSW {
              config false;
              description
              "This parameter reports a count of the successful
              bit swap (BSW) primitives.  This parameter is
              defined as success_BSW in clause 7.7.20 of  ITU-T
              Rec.  {{bibref|G.997.2}}.";
              type uint32;
            }
            leaf SuccessSRA {
              config false;
              description
              "This parameter reports a count of the successful
              autonomous SRA (seamless rate adaptation)
              primitives.  This parameter is defined as
              success_SRA in clause 7.7.21 of  ITU-T Rec.
              {{bibref|G.997.2}}.";
              type uint32;
            }
            leaf SuccessFRA {
              config false;
              description
              "This parameter reports a count of the successful
              FRA (fast rate adaptation)  primitives.  This
              parameter is defined as success_FRA in clause
              7.7.22 of  ITU-T Rec.  {{bibref|G.997.2}}.";
              type uint32;
            }
            leaf SuccessRPA {
              config false;
              description
              "This parameter reports a count of the successful
              RPA (RMC parameter adjustment)  primitives.  This
              parameter is defined as success_RPA in clause
              7.7.23 of  ITU-T Rec.  {{bibref|G.997.2}}.";
              type uint32;
            }
            leaf SuccessTIGA {
              config false;
              description
              "This parameter reports a count of the successful
              TIGA (transmitter initiated gain adjustment)
              primitives.  This parameter is defined as
              success_TIGA in clause 7.7.24 of  ITU-T Rec.
              {{bibref|G.997.2}}.";
              type uint32;
            }
          }
          container CurrentDay {
            description
            "Note: The Total parameters SHOULD NOT be reset when
            the interface statistics are reset via an interface
            disable / enable cycle.";
            leaf ErroredSecs {
              config false;
              description
              "Total number of errored seconds as defined in
              ITU-T Rec.  {{bibref|G.997.2}}. An errored second
              (ES) is declared if, during a 1-second interval,
              there are one or more crc anomalies, or one or
              more los defects, or one or more lor defects, or
              one or more lpr primitives.";
              type uint32;
            }
            leaf SeverelyErroredSecs {
              config false;
              description
              "Total number of severely errored seconds as
              defined in ITU-T Rec.  {{bibref|G.997.2}}.";
              type uint32;
            }
            leaf LOSS {
              config false;
              description
              "Total number of loss of signal seconds (LOSS) as
              defined in ITU-T Rec.  {{bibref|G.997.2}}. A LOSS
              is declared if, during a 1-second interval, there
              are one or more los defects.";
              type uint32;
            }
            leaf LORS {
              config false;
              description
              "Total number of loss of RMC seconds (LORS) as
              defined in ITU-T Rec.  {{bibref|G.997.2}}. A LORS
              is declared if, during a 1-second interval, there
              are one or more lor defects.";
              type uint32;
            }
            leaf UAS {
              config false;
              description
              "Total number of unavailable seconds (UAS) as
              defined in ITU-T Rec.  {{bibref|G.997.2}}.";
              type uint32;
            }
            leaf RTXUC {
              config false;
              description
              "This parameter reports a count of uncorrected DTU
              anomalies (rtx_uc). This parameter is defined in
              clause 7.8.5 of ITU-T Rec.  {{bibref|G.997.2}}.";
              type uint32;
            }
            leaf RTXTX {
              config false;
              description
              "This parameter reports a count of retransmitted
              DTU anomalies (rtx_tx). This parameter is defined
              in clause 7.8.6 of ITU-T Rec.
              {{bibref|G.997.2}}.";
              type uint32;
            }
            leaf SuccessBSW {
              config false;
              description
              "This parameter reports a count of the successful
              bit swap (BSW) primitives.  This parameter is
              defined as success_BSW in clause 7.7.20 of  ITU-T
              Rec.  {{bibref|G.997.2}}.";
              type uint32;
            }
            leaf SuccessSRA {
              config false;
              description
              "This parameter reports a count of the successful
              autonomous SRA (seamless rate adaptation)
              primitives.  This parameter is defined as
              success_SRA in clause 7.7.21 of  ITU-T Rec.
              {{bibref|G.997.2}}.";
              type uint32;
            }
            leaf SuccessFRA {
              config false;
              description
              "This parameter reports a count of the successful
              FRA (fast rate adaptation)  primitives.  This
              parameter is defined as success_FRA in clause
              7.7.22 of  ITU-T Rec.  {{bibref|G.997.2}}.";
              type uint32;
            }
            leaf SuccessRPA {
              config false;
              description
              "This parameter reports a count of the successful
              RPA (RMC parameter adjustment)  primitives.  This
              parameter is defined as success_RPA in clause
              7.7.23 of  ITU-T Rec.  {{bibref|G.997.2}}.";
              type uint32;
            }
            leaf SuccessTIGA {
              config false;
              description
              "This parameter reports a count of the successful
              TIGA (transmitter initiated gain adjustment)
              primitives.  This parameter is defined as
              success_TIGA in clause 7.7.24 of  ITU-T Rec.
              {{bibref|G.997.2}}.";
              type uint32;
            }
          }
          container QuarterHour {
            description
            "Note: The Total parameters SHOULD NOT be reset when
            the interface statistics are reset via an interface
            disable / enable cycle.";
            leaf ErroredSecs {
              config false;
              description
              "Total number of errored seconds as defined in
              ITU-T Rec.  {{bibref|G.997.2}}. An errored second
              (ES) is declared if, during a 1-second interval,
              there are one or more crc anomalies, or one or
              more los defects, or one or more lor defects, or
              one or more lpr primitives.";
              type uint32;
            }
            leaf SeverelyErroredSecs {
              config false;
              description
              "Total number of severely errored seconds as
              defined in ITU-T Rec.  {{bibref|G.997.2}}.";
              type uint32;
            }
            leaf LOSS {
              config false;
              description
              "Total number of loss of signal seconds (LOSS) as
              defined in ITU-T Rec.  {{bibref|G.997.2}}. A LOSS
              is declared if, during a 1-second interval, there
              are one or more los defects.";
              type uint32;
            }
            leaf LORS {
              config false;
              description
              "Total number of loss of RMC seconds (LORS) as
              defined in ITU-T Rec.  {{bibref|G.997.2}}. A LORS
              is declared if, during a 1-second interval, there
              are one or more lor defects.";
              type uint32;
            }
            leaf UAS {
              config false;
              description
              "Total number of unavailable seconds (UAS) as
              defined in ITU-T Rec.  {{bibref|G.997.2}}.";
              type uint32;
            }
            leaf RTXUC {
              config false;
              description
              "This parameter reports a count of uncorrected DTU
              anomalies (rtx_uc). This parameter is defined in
              clause 7.8.5 of ITU-T Rec.  {{bibref|G.997.2}}.";
              type uint32;
            }
            leaf RTXTX {
              config false;
              description
              "This parameter reports a count of retransmitted
              DTU anomalies (rtx_tx). This parameter is defined
              in clause 7.8.6 of ITU-T Rec.
              {{bibref|G.997.2}}.";
              type uint32;
            }
            leaf SuccessBSW {
              config false;
              description
              "This parameter reports a count of the successful
              bit swap (BSW) primitives.  This parameter is
              defined as success_BSW in clause 7.7.20 of  ITU-T
              Rec.  {{bibref|G.997.2}}.";
              type uint32;
            }
            leaf SuccessSRA {
              config false;
              description
              "This parameter reports a count of the successful
              autonomous SRA (seamless rate adaptation)
              primitives.  This parameter is defined as
              success_SRA in clause 7.7.21 of  ITU-T Rec.
              {{bibref|G.997.2}}.";
              type uint32;
            }
            leaf SuccessFRA {
              config false;
              description
              "This parameter reports a count of the successful
              FRA (fast rate adaptation)  primitives.  This
              parameter is defined as success_FRA in clause
              7.7.22 of  ITU-T Rec.  {{bibref|G.997.2}}.";
              type uint32;
            }
            leaf SuccessRPA {
              config false;
              description
              "This parameter reports a count of the successful
              RPA (RMC parameter adjustment)  primitives.  This
              parameter is defined as success_RPA in clause
              7.7.23 of  ITU-T Rec.  {{bibref|G.997.2}}.";
              type uint32;
            }
            leaf SuccessTIGA {
              config false;
              description
              "This parameter reports a count of the successful
              TIGA (transmitter initiated gain adjustment)
              primitives.  This parameter is defined as
              success_TIGA in clause 7.7.24 of  ITU-T Rec.
              {{bibref|G.997.2}}.";
              type uint32;
            }
          }
        }
        container TestParams {
          description
          "This object contains the FAST line test parameters
          that are available during the L0 (i.e., Showtime)
          state.";
          leaf SNRGds {
            config false;
            description
            "Note: In ITU-T G.9701-2014, the only valid value is
            G = 1. See clause 7.10.8.2 ITU-T Recommendation
            {{bibref|G.997.2}}.";
            type uint32;
          }
          leaf SNRGus {
            config false;
            description
            "Note: In ITU-T G.9701-2014, the only valid value is
            G = 1. See clause 7.10.8.5 ITU-T Recommendation
            {{bibref|G.997.2}}.";
            type uint32;
          }
          leaf-list SNRpsds {
            config false;
            description
            "Note: See clause 7.10.8.3 of ITU-T Recommendation
            {{bibref|G.997.2}}.";
            type int32;
          }
          leaf-list SNRpsus {
            config false;
            description
            "Note: See clause 7.10.8.6 of ITU-T Recommendation
            {{bibref|G.997.2}}.";
            type string;
          }
          leaf SNRMTds {
            config false;
            description
            "Note: See clause 7.10.8.1 of ITU-T Recommendation
            {{bibref|G.997.2}}.";
            type uint32;
          }
          leaf SNRMTus {
            config false;
            description
            "Note: See clause 7.10.8.4 of ITU-T Recommendation
            {{bibref|G.997.2}}.";
            type uint32;
          }
          leaf ACTINP {
            config false;
            description
            "Note: See ITU-T Recommendation {{bibref|G.997.2}}.";
            type uint32;
          }
          leaf NFEC {
            config false;
            description
            "Note: See clause 7.11.4.1 ITU-T Recommendation
            {{bibref|G.997.2}}.";
            type uint32;
          }
          leaf RFEC {
            config false;
            description
            "Note: See ITU-T Recommendation {{bibref|G.997.2}}.";
            type int32;
          }
          leaf UpstreamCurrRate {
            config false;
            description
            "The current physical layer aggregate data rate
            (expressed in Kbps) of the upstream FAST
            connection.  The valid values are 0..4294967295(0
            to 232-1 kbit/s).";
            type uint32;
          }
          leaf DownstreamCurrRate {
            config false;
            description
            "The current physical layer aggregate data rate
            (expressed in Kbps) of the downstream FAST
            connection.  The valid values are 0..4294967295(0
            to 232-1 kbit/s).";
            type uint32;
          }
          leaf ACTINPREIN {
            config false;
            description
            "Reports the actual INP against REIN as defined in
            clause 11.4.1.1.8/{{bibref|G.9701}}. A special
            value indicates an actual INP against REIN of 63
            symbols or higher.  The valid range is 0..62
            symbols, and 63 is the special value.";
            type uint32;
          }
        }
      }
    }
    container Optical {
      description
      "This object models optical interface technologies.  It
      defines an {{object|Interface}} object that models a
      layer 1 optical interface that is capable of transporting
      Ethernet packets.  The data model definition is based on
      parts of {{bibref|G.988}}.";
      leaf InterfaceNumberOfEntries {
        config false;
        description
        "{{numentries}}";
        type uint32;
      }
      list Interface {
        key "Name";
        unique "Alias";
        config true;
        description
        "Optical interface table (a stackable interface object
        as described in {{bibref|TR-181i2|Section 4.2}}).  This
        table models physical optical interfaces.";
        leaf Enable {
          config true;
          description
          "This parameter is based on ''ifAdminStatus'' from
          {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config true;
          description
          "The textual name of the optical interface as assigned
          by the CPE.";
          type string {
            length "0..64";
          }
        }
        leaf LastChange {
          config false;
          description
          "The accumulated time in {{units}} since the optical
          interface entered its current operational state.";
          type uint32;
        }
        leaf-list LowerLayers {
          config true;
          description
          "Note: Since {{object}} is a layer 1 interface, it is
          expected that {{param}} will not be used.";
          type string;
        }
        leaf Upstream {
          config false;
          description
          "* For an End Device, {{param}} will be {{true}} for
          all interfaces.";
          type boolean;
        }
        leaf OpticalSignalLevel {
          config false;
          description
          "This parameter is based on ''Optical signal level''
          from {{bibref|G.988|Section 9.2.1}}.";
          type Dbm1000;
        }
        leaf LowerOpticalThreshold {
          config false;
          description
          "This parameter is based on ''Lower optical
          threshold'' from {{bibref|G.988|section 9.2.1}}.";
          type Dbm1000;
        }
        leaf UpperOpticalThreshold {
          config false;
          description
          "This parameter is based on ''Upper optical
          threshold'' from {{bibref|G.988|section 9.2.1}}.";
          type Dbm1000;
        }
        leaf TransmitOpticalLevel {
          config false;
          description
          "This parameter is based on ''Transmit optical level''
          from {{bibref|G.988|section 9.2.1}}.";
          type Dbm1000;
        }
        leaf LowerTransmitPowerThreshold {
          config false;
          description
          "This parameter is based on ''Lower transmit power
          threshold'' from {{bibref|G.988|section 9.2.1}}.";
          type Dbm1000;
        }
        leaf UpperTransmitPowerThreshold {
          config false;
          description
          "This parameter is based on ''Upper transmit power
          threshold'' from {{bibref|G.988|section 9.2.1}}.";
          type Dbm1000;
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to prevent their being delivered.
            One possible reason for discarding such a packet
            could be to free up buffer space.";
            type uint32;
          }
        }
      }
    }
    container Cellular {
      description
      "This object models cellular interfaces and access points.";
      leaf RoamingEnabled {
        config true;
        description
        "Enables or disables roaming.";
        type boolean;
      }
      leaf RoamingStatus {
        config false;
        description
        "Current roaming status.";
        type enumeration {
          enum "Home";
          enum "Roaming";
        }
      }
      leaf InterfaceNumberOfEntries {
        config false;
        description
        "{{numentries}}";
        type uint32;
      }
      leaf AccessPointNumberOfEntries {
        config false;
        description
        "{{numentries}}";
        type uint32;
      }
      list Interface {
        key "Name";
        unique "Alias";
        config true;
        description
        "Cellular interface table (a stackable interface object
        as described in {{bibref|TR-181i2|Section 4.2}}).  Each
        instance of this object models a cellular modem with a
        single radio and a single {{object|USIM}}.";
        leaf Enable {
          config true;
          description
          "This parameter is based on ''ifAdminStatus'' from
          {{bibref|RFC2863}}.";
          type boolean;
        }
        leaf Status {
          config false;
          description
          "This parameter is based on ''ifOperStatus'' from
          {{bibref|RFC2863}}.";
          type enumeration {
            enum "Up" {
              description
              "Corresponds to
              {{enum|GPRS|CurrentAccessTechnology}},
              {{enum|UMTS|CurrentAccessTechnology}},
              {{enum|LTE|CurrentAccessTechnology}} etc
              ''ATTACHED'' status";
            }
            enum "Down";
            enum "Unknown";
            enum "Dormant";
            enum "NotPresent" {
              description
              "Corresponds to
              {{enum|GPRS|CurrentAccessTechnology}},
              {{enum|UMTS|CurrentAccessTechnology}},
              {{enum|LTE|CurrentAccessTechnology}} etc
              ''DETACHED'' status";
            }
            enum "LowerLayerDown";
            enum "Error";
          }
        }
        leaf Alias {
          config true;
          description
          "{{datatype|expand}}";
          type Alias;
        }
        leaf Name {
          config true;
          description
          "The textual name of the interface as assigned by the
          CPE.";
          type string {
            length "0..64";
          }
        }
        leaf LastChange {
          config false;
          description
          "The accumulated time in {{units}} since the interface
          entered its current operational state.";
          type uint32;
        }
        leaf-list LowerLayers {
          config true;
          description
          "Note: Since {{object}} is a layer 1 interface, it is
          expected that {{param}} will not be used.";
          type string;
        }
        leaf Upstream {
          config false;
          description
          "* For an End Device, {{param}} will be {{true}} for
          all interfaces.";
          type boolean;
        }
        leaf IMEI {
          config false;
          description
          "International Mobile Station Equipment Identity
          number, represented as a 15 digit string (digits
          0-9).";
          type string {
            length "15";
            pattern "[0-9]{15,15}";
          }
        }
        leaf-list SupportedAccessTechnologies {
          config false;
          description
          "Access technologies supported by the interface.";
          type enumeration {
            enum "GPRS" {
              description
              "GSM with GPRS";
            }
            enum "EDGE" {
              description
              "GSM with EDGE";
            }
            enum "UMTS";
            enum "UMTSHSPA" {
              description
              "UMTS with High Speed Packet Access (HSPA
              {{bibref|3GPP-HSPA}})";
            }
            enum "CDMA2000OneX";
            enum "CDMA2000HRPD";
            enum "LTE";
          }
        }
        leaf PreferredAccessTechnology {
          config true;
          description
          "Preferred access technology.";
          type string;
          default "Auto";
          must ". = ../SupportedAccessTechnologies";
        }
        leaf CurrentAccessTechnology {
          config false;
          description
          "Access technology that is currently in use.";
          type string;
          must ". = ../SupportedAccessTechnologies";
        }
        leaf-list AvailableNetworks {
          config false;
          description
          "List of available networks.";
          type string {
            length "0..64";
          }
        }
        leaf NetworkRequested {
          config true;
          description
          "Name of the network which will be used, or {{empty}}
          if the network is selected automatically.";
          type string {
            length "0..64";
          }
        }
        leaf NetworkInUse {
          config false;
          description
          "The value is {{empty}} if no network is found, or if
          the network specified in {{param|NetworkRequested}}
          is not found.";
          type string {
            length "0..64";
          }
          must ". = ../AvailableNetworks";
        }
        leaf RSSI {
          config false;
          description
          "Note: An undetectable signal is indicated by the
          appropriate lower limit, e.g.  -117 {{units}} for
          LTE.";
          type int32;
        }
        leaf UpstreamMaxBitRate {
          config false;
          description
          "The current maximum attainable data rate upstream
          (expressed in {{units}}).";
          type uint32;
        }
        leaf DownstreamMaxBitRate {
          config false;
          description
          "The current maximum attainable data rate downstream
          (expressed in {{units}}).";
          type uint32;
        }
        container USIM {
          description
          "USIM (Universal Subscriber Identity Module or SIM
          card) parameters for the interface.";
          leaf Status {
            config false;
            description
            "The current status of the USIM card.";
            type enumeration {
              enum "None" {
                description
                "No card available";
              }
              enum "Available" {
                description
                "Card is available but not verified";
              }
              enum "Valid" {
                description
                "Card can be used; either valid PIN was entered,
                or PIN check is deactivated";
              }
              enum "Blocked" {
                description
                "USIM is blocked because the maximum number of
                invalid PIN entries was exceeded";
              }
              enum "Error" {
                description
                "An error was detected with the card";
              }
            }
          }
          leaf IMSI {
            config false;
            description
            "International Mobile Subscriber Identity
            represented as a string with either 14 or 15 digits
            (digits 0-9). The first 3 digits are the mobile
            country code (MCC), which are followed by the
            mobile network code (MNC), either 2 digits
            (European standard) or 3 digits (North American
            standard), followed by the mobile subscription
            identification number (MSIN).";
            type string {
              length "14..15";
              pattern "[0-9]{14,15}";
            }
          }
          leaf ICCID {
            config false;
            description
            "For cards using an ICCID according to
            {{bibref|ITU-E.118}} the maximum length is 19
            Digits, for GSM cards 20 digits.";
            type string {
              length "6..20";
              pattern "[0-9]{6,20}";
            }
          }
          leaf MSISDN {
            config false;
            description
            "Mobile Subscriber Integrated Service Digital
            Network Number, a number uniquely identifying a
            subscription in a GSM, UMTS, or LTE mobile network.
            {{bibref|ITU-E.164}}";
            type string {
              length "14..15";
              pattern "[0-9]{14,15}";
            }
          }
          leaf PINCheck {
            config true;
            description
            "Controls the PIN verification of the USIM card.";
            type enumeration {
              enum "OnNetworkAccess" {
                description
                "Check the PIN with each access to a new network";
              }
              enum "Reboot" {
                description
                "Check the PIN with first access after (re)boot";
              }
              enum "Off" {
                description
                "Disable the PIN check";
              }
            }
          }
          leaf PIN {
            config true;
            description
            "Allows the ACS to change the USIM PIN used for SIM
            card activation.";
            type string {
              length "0..4";
            }
          }
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type yang:counter32;
          }
          leaf BytesReceived {
            config false;
            description
            "The total number of bytes received on the
            interface, including framing characters.";
            type yang:counter32;
          }
          leaf PacketsSent {
            config false;
            description
            "The total number of packets transmitted out of the
            interface.";
            type yang:counter32;
          }
          leaf PacketsReceived {
            config false;
            description
            "The total number of packets received on the
            interface.";
            type yang:counter32;
          }
          leaf ErrorsSent {
            config false;
            description
            "The total number of outbound packets that could not
            be transmitted because of errors.";
            type yang:counter32;
          }
          leaf ErrorsReceived {
            config false;
            description
            "The total number of inbound packets that contained
            errors preventing them from being delivered to a
            higher-layer protocol.";
            type yang:counter32;
          }
          leaf UnicastPacketsSent {
            config false;
            description
            "The total number of packets requested for
            transmission which were not addressed to a
            multicast or broadcast address at this layer,
            including those that were discarded or not sent.";
            type yang:counter32;
          }
          leaf UnicastPacketsReceived {
            config false;
            description
            "The total number of received packets, delivered by
            this layer to a higher layer, which were not
            addressed to a multicast or broadcast address at
            this layer.";
            type yang:counter32;
          }
          leaf DiscardPacketsSent {
            config false;
            description
            "The total number of outbound packets which were
            chosen to be discarded even though no errors had
            been detected to prevent their being transmitted.
            One possible reason for discarding such a packet
            could be to free up buffer space.";
            type yang:counter32;
          }
          leaf DiscardPacketsReceived {
            config false;
            description
            "The total number of inbound packets which were
            chosen to be discarded even though no errors had
            been detected to  prevent their being delivered.
            One possible reason for discarding such a packet
            could be to free up buffer space.";
            type yang:counter32;
          }
          leaf MulticastPacketsSent {
            config false;
            description
            "The total number of packets that higher-level
            protocols requested for transmission and which were
            addressed to a multicast address at this layer,
            including those that were discarded or not sent.";
            type yang:counter32;
          }
          leaf MulticastPacketsReceived {
            config false;
            description
            "The total number of received packets, delivered by
            this layer to a higher layer, which were addressed
            to a multicast address at this layer.";
            type yang:counter32;
          }
          leaf BroadcastPacketsSent {
            config false;
            description
            "The total number of packets that higher-level
            protocols requested for transmission and which were
            addressed to a broadcast address at this layer,
            including those that were discarded or not sent.";
            type yang:counter32;
          }
          leaf BroadcastPacketsReceived {
            config false;
            description
            "The total number of received packets, delivered by
            this layer to a higher layer, which were addressed
            to a broadcast address at this layer.";
            type yang:counter32;
          }
          leaf UnknownProtoPacketsReceived {
            config false;
            description
            "The total number of packets received via the
            interface which were discarded because of an
            unknown or unsupported  protocol.";
            type yang:counter32;
          }
        }
      }
      list AccessPoint {
        key "APN";
        unique "Alias";
        unique "Interface";
        config true;
        description
        "Cellular Access Point table.  Each entry is identified
        by an {{param|APN}} (Access Point Name) that identifies
        a gateway between the mobile network and another
        computer network.";
        leaf Enable {
          config true;
          description
          "Enables or disables the Access Point.";
          type boolean;
        }
        leaf Alias {
          config true;
          description
          "{{datatype|expand}}";
          type Alias;
        }
        leaf APN {
          config true;
          description
          "Access Point Name.";
          type string {
            length "0..64";
          }
        }
        leaf Username {
          config true;
          description
          "Username used to authenticate the CPE when making a
          connection to the Access Point.";
          type string {
            length "0..256";
          }
        }
        leaf Password {
          config true;
          description
          "Password used to authenticate the CPE when making a
          connection to the Access Point.";
          type string {
            length "0..256";
          }
        }
        leaf Proxy {
          config true;
          description
          "Proxy server IP address.";
          type inet:ip-address;
        }
        leaf ProxyPort {
          config true;
          description
          "Proxy server port.";
          type uint32 {
            range "1..65535";
          }
        }
        leaf Interface {
          config true;
          description
          "Reference to the interface with which the access
          point is associated.";
          type string;
        }
      }
    }
    container ATM {
      description
      "Asynchronous Transfer Mode (ATM) object that contains the
      {{object|Link}} interface and
      {{object|Diagnostics.F5Loopback}} diagnostics.";
      leaf LinkNumberOfEntries {
        config false;
        description
        "{{numentries}}";
        type uint32;
      }
      list Link {
        key "Name";
        unique "Alias";
        config true;
        description
        "When an ''ATM Link'' interface is used, a lower-layer
        {{object|.DSL.Channel}} interface MUST be configured
        with ATM encapsulation (see
        {{param|.DSL.Channel.{i}.LinkEncapsulationUsed}}).";
        leaf Enable {
          config true;
          description
          "This parameter is based on ''ifAdminStatus'' from
          {{bibref|RFC2863}}.";
          type boolean;
          default "false";
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
          default "Down";
        }
        leaf Alias {
          config true;
          description
          "{{datatype|expand}}";
          type Alias;
        }
        leaf Name {
          config true;
          description
          "The textual name of the link as assigned by the CPE.";
          type string {
            length "0..64";
          }
        }
        leaf LastChange {
          config false;
          description
          "The accumulated time in {{units}} since the link
          entered its current operational state.";
          type uint32;
        }
        leaf-list LowerLayers {
          config true;
          description
          "{{list}} {{reference|an interface object that is
          stacked immediately below this interface object}}
          See {{bibref|TR-181i2|Section 4.2.1}}.";
          type string;
        }
        leaf LinkType {
          config true;
          description
          "Indicates the type of connection and refers to the
          complete stack of protocol used for this connection.";
          type enumeration {
            enum "EoA" {
              description
              "{{bibref|RFC2684}} bridged Ethernet over ATM";
            }
            enum "IPoA" {
              description
              "{{bibref|RFC2684}} routed IP over ATM";
            }
            enum "PPPoA" {
              description
              "{{bibref|RFC2364}} PPP over ATM";
            }
            enum "CIP" {
              description
              "{{bibref|RFC2225}} Classical IP over ATM";
            }
            enum "Unconfigured";
          }
        }
        leaf AutoConfig {
          config false;
          description
          "Indicates if the CPE is currently using some auto
          configuration mechanisms for this connection.  If
          this  variable is {{true}}, all writable variables in
          this connection instance become read-only.  Any
          attempt to change one of these variables SHOULD fail
          and an error SHOULD be returned.";
          type boolean;
        }
        leaf DestinationAddress {
          config true;
          description
          "Destination address of this link, in the form
          \"VPI/VCI\" (e.g.  \"8/23\" or \"0/35\").";
          type string {
            length "0..256";
            pattern "\\d+/\\d+";
          }
        }
        leaf Encapsulation {
          config true;
          description
          "Identifies the connection encapsulation that will be
          used.";
          type enumeration {
            enum "LLC";
            enum "VCMUX";
          }
        }
        leaf FCSPreserved {
          config true;
          description
          "This flag tells if a checksum SHOULD be added in the
          ATM payload.  It does not refer to the checksum of
          one of  the ATM cells or AALX packets.  In case of
          LLC or VCMUX encapsulation, this ATM checksum is the
          FCS field described in {{bibref|RFC2684}}. It is only
          applicable in the upstream direction.";
          type boolean;
        }
        leaf-list VCSearchList {
          config true;
          description
          ": ''0/35, 8/35, 1/35''";
          type string {
            pattern "\\d+/\\d+";
          }
        }
        leaf AAL {
          config false;
          description
          "Describes the ATM Adaptation Layer (AAL) currently in
          use on the PVC.";
          type enumeration {
            enum "AAL1";
            enum "AAL2";
            enum "AAL3";
            enum "AAL4";
            enum "AAL5";
          }
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "The total number of packets that higher-level
            protocols requested for transmission and which were
            addressed to a broadcast address at this layer,
            including those that were discarded or not sent.";
            type uint64;
          }
          leaf BroadcastPacketsReceived {
            config false;
            description
            "The total number of received packets, delivered by
            this layer to a higher layer, which were addressed
            to a broadcast address at this layer.";
            type uint64;
          }
          leaf UnknownProtoPacketsReceived {
            config false;
            description
            "The total number of packets received via the
            interface which were discarded because of an
            unknown or unsupported  protocol.";
            type uint32;
          }
          leaf TransmittedBlocks {
            config false;
            description
            "The current count of successfully transmitted
            cells.";
            type uint32;
          }
          leaf ReceivedBlocks {
            config false;
            description
            "The current count of successfully received cells.";
            type uint32;
          }
          leaf CRCErrors {
            config false;
            description
            "This refers to CRC errors at the ATM adaptation
            layer (AAL). The AAL in use is indicated by the
            {{param|#.AAL}} parameter.  The value  of the
            {{param}} parameter MUST be 0 for AAL types that
            have no CRCs.";
            type uint32;
          }
          leaf HECErrors {
            config false;
            description
            "Count of the number of Header Error Check related
            errors at the ATM layer.";
            type uint32;
          }
        }
        container QoS {
          description
          "The ATM Link QoS object.";
          leaf QoSClass {
            config true;
            description
            "Describes the ATM Quality Of Service (QoS) being
            used on the VC.";
            type enumeration {
              enum "UBR";
              enum "CBR";
              enum "GFR";
              enum "VBR-nrt";
              enum "VBR-rt";
              enum "UBR+";
              enum "ABR";
            }
          }
          leaf PeakCellRate {
            config true;
            description
            "Specifies the upstream peak cell rate in {{units}}.";
            type uint32;
          }
          leaf MaximumBurstSize {
            config true;
            description
            "Specifies the upstream maximum burst size in
            {{units}}.";
            type uint32;
          }
          leaf SustainableCellRate {
            config true;
            description
            "Specifies the upstream sustainable cell rate, in
            {{units}}.";
            type uint32;
          }
        }
      }
      container Diagnostics {
        description
        "The ATM Diagnostics object.";
        container F5Loopback {
          description
          "This object provides access to an ATM-layer F5 OAM
          loopback test.";
          leaf DiagnosticsState {
            config true;
            description
            "{{datatype|expand}}";
            type DiagnosticsState;
          }
          leaf Interface {
            config true;
            description
            "{{reference}}  This is the interface over which the
            test is to be performed.";
            type string {
              length "0..256";
            }
          }
          leaf NumberOfRepetitions {
            config true;
            description
            "Number of repetitions of the ping test to perform
            before reporting the results.";
            type uint32 {
              range "1..max";
            }
          }
          leaf Timeout {
            config true;
            description
            "Timeout in {{units}} for the ping test.";
            type uint32 {
              range "1..max";
            }
          }
          leaf SuccessCount {
            config false;
            description
            "Result parameter indicating the number of
            successful pings (those in which a successful
            response was received  prior to the timeout) in the
            most recent ping test.";
            type uint32;
          }
          leaf FailureCount {
            config false;
            description
            "Result parameter indicating the number of failed
            pings in the most recent ping test.";
            type uint32;
          }
          leaf AverageResponseTime {
            config false;
            description
            "Result parameter indicating the average response
            time in {{units}} over all repetitions with
            successful  responses of the most recent ping test.
            If there were no successful responses, this value
            MUST be zero.";
            type uint32;
          }
          leaf MinimumResponseTime {
            config false;
            description
            "Result parameter indicating the minimum response
            time in {{units}} over all repetitions with
            successful  responses of the most recent ping test.
            If there were no successful responses, this value
            MUST be zero.";
            type uint32;
          }
          leaf MaximumResponseTime {
            config false;
            description
            "Result parameter indicating the maximum response
            time in {{units}} over all repetitions with
            successful  responses of the most recent ping test.
            If there were no successful responses, this value
            MUST be zero.";
            type uint32;
          }
        }
      }
    }
    container PTM {
      description
      "Packet Transfer Mode ({{bibref|G.993.1|Annex H}}). This
      object contains the {{object|Link}} interface.";
      leaf LinkNumberOfEntries {
        config false;
        description
        "{{numentries}}";
        type uint32;
      }
      list Link {
        key "Name";
        unique "Alias";
        config true;
        description
        "When a ''PTM Link'' interface is used, a lower-layer
        {{object|.DSL.Channel}} interface MUST be configured
        with PTM encapsulation (see
        {{param|.DSL.Channel.{i}.LinkEncapsulationUsed}}).";
        leaf Enable {
          config true;
          description
          "This parameter is based on ''ifAdminStatus'' from
          {{bibref|RFC2863}}.";
          type boolean;
          default "false";
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
          default "Down";
        }
        leaf Alias {
          config true;
          description
          "{{datatype|expand}}";
          type Alias;
        }
        leaf Name {
          config true;
          description
          "The textual name of the link as assigned by the CPE.";
          type string {
            length "0..64";
          }
        }
        leaf LastChange {
          config false;
          description
          "The accumulated time in {{units}} since the link
          entered its current operational state.";
          type uint32;
        }
        leaf-list LowerLayers {
          config true;
          description
          "{{list}} {{reference|an interface object that is
          stacked immediately below this interface object}}
          See {{bibref|TR-181i2|Section 4.2.1}}.";
          type string;
        }
        leaf MACAddress {
          config false;
          description
          "Note: This is not necessarily the same as the
          Ethernet header source or destination MAC address,
          which is associated with the IP interface and is
          modeled via the
          {{param|.Ethernet.Link.{i}.MACAddress}} parameter.";
          type yang:mac-address;
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "The total number of packets that higher-level
            protocols requested for transmission and which were
            addressed to a broadcast address at this layer,
            including those that were discarded or not sent.";
            type uint64;
          }
          leaf BroadcastPacketsReceived {
            config false;
            description
            "The total number of received packets, delivered by
            this layer to a higher layer, which were addressed
            to a broadcast address at this layer.";
            type uint64;
          }
          leaf UnknownProtoPacketsReceived {
            config false;
            description
            "The total number of packets received via the
            interface which were discarded because of an
            unknown or unsupported  protocol.";
            type uint32;
          }
        }
      }
    }
    container Ethernet {
      description
      "Ethernet object.  This object models several Ethernet
      interface objects, each representing a different stack
      layer, including: {{object|Interface}}, {{object|Link}},
      and {{object|VLANTermination}}. {{object|Interface}} is
      media-specific and models a port, the PHY layer, and the
      MAC layer.  {{object|Link}} is media-independent and
      models the Logical Link Control (LLC) layer.  An
      \"outer\" {{object|VLANTermination}}, when present, is
      expected to be stacked on top of {{object|Link}} objects
      to receive and send frames with a configured VLANID.";
      leaf InterfaceNumberOfEntries {
        config false;
        description
        "{{numentries}}";
        type uint32;
      }
      leaf LinkNumberOfEntries {
        config false;
        description
        "{{numentries}}";
        type uint32;
      }
      leaf VLANTerminationNumberOfEntries {
        config false;
        description
        "{{numentries}}";
        type uint32;
      }
      leaf RMONStatsNumberOfEntries {
        config false;
        description
        "{{numentries}}";
        type uint32;
      }
      leaf LAGNumberOfEntries {
        config false;
        description
        "{{numentries}}";
        type uint32;
      }
      list Interface {
        key "Name";
        unique "Alias";
        config true;
        description
        "Ethernet interface table (a stackable interface object
        as described in {{bibref|TR-181i2|Section 4.2}}). This
        table models physical Ethernet ports, but in terms of
        the interface stack it also models the PHY and MAC
        level Ethernet interface.";
        leaf Enable {
          config true;
          description
          "This parameter is based on ''ifAdminStatus'' from
          {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config true;
          description
          "The textual name of the interface as assigned by the
          CPE.";
          type string {
            length "0..64";
          }
        }
        leaf LastChange {
          config false;
          description
          "The accumulated time in {{units}} since the interface
          entered its current operational state.";
          type uint32;
        }
        leaf-list LowerLayers {
          config true;
          description
          "Note: Since {{object}} is a layer 1 interface, it is
          expected that {{param}} will not be used.";
          type string;
        }
        leaf Upstream {
          config false;
          description
          "* For an End Device, {{param}} will be {{true}} for
          all interfaces.";
          type boolean;
        }
        leaf MACAddress {
          config false;
          description
          "Note: This is not necessarily the same as the
          Ethernet header source or destination MAC address,
          which is associated with the IP interface and is
          modeled via the
          {{param|.Ethernet.Link.{i}.MACAddress}} parameter.";
          type yang:mac-address;
        }
        leaf MaxBitRate {
          config true;
          description
          "A value of -1 indicates automatic selection of the
          maximum bit rate.";
          type int32 {
            range "-1..max";
          }
        }
        leaf CurrentBitRate {
          config false;
          description
          "A value of 0 indicates that the current bit rate is
          unknown.";
          type uint32;
        }
        leaf DuplexMode {
          config true;
          description
          "The duplex mode available to this connection.";
          type enumeration {
            enum "Half";
            enum "Full";
            enum "Auto";
          }
        }
        leaf EEECapability {
          config false;
          description
          "Indicates whether this physical ethernet port
          supports Energy Efficient Ethernet as specified in
          {{bibref|802.3-2012_section6|Section 78}}.";
          type boolean;
        }
        leaf EEEEnable {
          config true;
          description
          "Whether Energy Efficient Ethernet
          {{bibref|802.3-2012_section6|Section 78}} support is
          currently enabled.  When enabled, this ethernet port
          will be capable of entering or exiting Low Power Idle
          (LPI) mode.";
          type boolean;
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "The total number of packets that higher-level
            protocols requested for transmission and which were
            addressed to a broadcast address at this layer,
            including those that were discarded or not sent.";
            type uint64;
          }
          leaf BroadcastPacketsReceived {
            config false;
            description
            "The total number of received packets, delivered by
            this layer to a higher layer, which were addressed
            to a broadcast address at this layer.";
            type uint64;
          }
          leaf UnknownProtoPacketsReceived {
            config false;
            description
            "The total number of packets received via the
            interface which were discarded because of an
            unknown or unsupported  protocol.";
            type uint32;
          }
        }
      }
      list Link {
        key "MACAddress";
        unique "Alias";
        unique "Name";
        config true;
        description
        "Ethernet link layer table (a stackable interface object
        as described in {{bibref|TR-181i2|Section 4.2}}). Table
        entries model the Logical Link Control (LLC) layer.  It
        is expected that an ''Ethernet Link'' interface can be
        stacked above any lower-layer interface object capable
        of carrying Ethernet frames.";
        leaf Enable {
          config true;
          description
          "This parameter is based on ''ifAdminStatus'' from
          {{bibref|RFC2863}}.";
          type boolean;
          default "false";
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
          default "Down";
        }
        leaf Alias {
          config true;
          description
          "{{datatype|expand}}";
          type Alias;
        }
        leaf Name {
          config false;
          description
          "The textual name of the link as assigned by the CPE.";
          type string {
            length "0..64";
          }
        }
        leaf LastChange {
          config false;
          description
          "The accumulated time in {{units}} since the link
          entered its current operational state.";
          type uint32;
        }
        leaf-list LowerLayers {
          config true;
          description
          "{{list}} {{reference|an interface object that is
          stacked immediately below this interface object}}
          See {{bibref|TR-181i2|Section 4.2.1}}.";
          type string;
        }
        leaf MACAddress {
          config true;
          description
          "The MAC address used for packets sent via this
          interface.  Provides the source MAC address for
          outgoing traffic and the destination MAC address for
          incoming traffic.";
          type yang:mac-address;
        }
        leaf PriorityTagging {
          config true;
          description
          "The parameter does not affect reception of ingress
          frames.";
          type boolean;
          default "false";
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "The total number of packets that higher-level
            protocols requested for transmission and which were
            addressed to a broadcast address at this layer,
            including those that were discarded or not sent.";
            type uint64;
          }
          leaf BroadcastPacketsReceived {
            config false;
            description
            "The total number of received packets, delivered by
            this layer to a higher layer, which were addressed
            to a broadcast address at this layer.";
            type uint64;
          }
          leaf UnknownProtoPacketsReceived {
            config false;
            description
            "The total number of packets received via the
            interface which were discarded because of an
            unknown or unsupported  protocol.";
            type uint32;
          }
        }
      }
      list VLANTermination {
        key "Name";
        unique "Alias";
        config true;
        description
        "VLAN Termination table (a stackable interface object as
        described in {{bibref|TR-181i2|Section 4.2}}). A VLAN
        Termination entry is typically stacked on top of a
        {{object|#.Link}} object to receive and send frames
        with the configured {{param|VLANID}}.";
        leaf Enable {
          config true;
          description
          "This parameter is based on ''ifAdminStatus'' from
          {{bibref|RFC2863}}.";
          type boolean;
          default "false";
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
          default "Down";
        }
        leaf Alias {
          config true;
          description
          "{{datatype|expand}}";
          type Alias;
        }
        leaf Name {
          config true;
          description
          "The textual name of the VLANTermination entry as
          assigned by the CPE.";
          type string {
            length "0..64";
          }
        }
        leaf LastChange {
          config false;
          description
          "The accumulated time in {{units}} since the
          VLANTermination entered its current operational
          state.";
          type uint32;
        }
        leaf-list LowerLayers {
          config true;
          description
          "{{list}} {{reference|an interface object that is
          stacked immediately below this interface object}}
          See {{bibref|TR-181i2|Section 4.2.1}}.";
          type string;
        }
        leaf VLANID {
          config true;
          description
          "The VLAN ID for this {{object}} entry (as defined in
          {{bibref|802.1Q-2011}}). Only ingress frames with
          this VLAN ID will be passed to higher protocol
          layers; frames sent from higher protocol layers will
          be tagged with this VLAN ID.";
          type uint32 {
            range "1..4094";
          }
        }
        leaf TPID {
          config true;
          description
          "*S-TAG 0x9100 = 37120";
          type uint32;
          default "33024";
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "The total number of packets that higher-level
            protocols requested for transmission and which were
            addressed to a broadcast address at this layer,
            including those that were discarded or not sent.";
            type uint64;
          }
          leaf BroadcastPacketsReceived {
            config false;
            description
            "The total number of received packets, delivered by
            this layer to a higher layer, which were addressed
            to a broadcast address at this layer.";
            type uint64;
          }
          leaf UnknownProtoPacketsReceived {
            config false;
            description
            "The total number of packets received via the
            interface which were discarded because of an
            unknown or unsupported  protocol.";
            type uint32;
          }
        }
      }
      list RMONStats {
        key "Interface VLANID Queue";
        unique "Alias";
        config true;
        description
        "Note: The {{object}} table includes unique key
        parameters that are strong references.  If a strongly
        referenced object is deleted, the CPE will set the
        referencing parameter to {{empty}}. However, doing so
        under these circumstances might cause the updated
        {{object}} row to then violate the table's unique key
        constraint; if this occurs, the CPE MUST set
        {{param|Status}} to {{enum|Error_Misconfigured|Status}}
        and disable the offending {{object}} row.";
        leaf Enable {
          config true;
          description
          "Enables or disables this instance.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Alias {
          config true;
          description
          "{{datatype|expand}}";
          type Alias;
        }
        leaf Name {
          config false;
          description
          "The textual name of the {{object}} entry as assigned
          by the CPE.";
          type string {
            length "0..64";
          }
        }
        leaf Interface {
          config true;
          description
          "The term \"capable of transporting
          Ethernet-encapsulated packets\" means \"has an
          Ethernet header\" and therefore refers to any
          interface that is at or below an
          ''Ethernet''.{{object|#.Link}} instance in the
          interface stack.";
          type string;
        }
        leaf VLANID {
          config true;
          description
          "A non-zero value indicates that only packets that
          have the the specified VLAN ID will be considered.";
          type uint32 {
            range "0..4094";
          }
        }
        leaf Queue {
          config true;
          description
          "Only packets that are sent to the referenced queue
          will be considered.";
          type string;
        }
        leaf AllQueues {
          config true;
          description
          "Indicates whether this instance applies to all
          queues.  If {{true}}, the value of {{param|Queue}} is
          ignored since all egress queues are indicated.";
          type boolean;
          default "false";
        }
        leaf DropEvents {
          config false;
          description
          "This parameter is based on ''etherStatsDropEvents''
          from {{bibref|RFC2819}}.";
          type uint32;
          default "0";
        }
        leaf Bytes {
          config false;
          description
          "This parameter is based on ''etherStatsOctets'' from
          {{bibref|RFC2819}}.";
          type uint64;
          default "0";
        }
        leaf Packets {
          config false;
          description
          "This parameter is based on ''etherStatsPkts'' from
          {{bibref|RFC2819}}.";
          type uint64;
          default "0";
        }
        leaf BroadcastPackets {
          config false;
          description
          "This parameter is based on
          ''etherStatsBroadcastPkts'' from {{bibref|RFC2819}}.";
          type uint64;
          default "0";
        }
        leaf MulticastPackets {
          config false;
          description
          "This parameter is based on
          ''etherStatsMulticastPkts'' from {{bibref|RFC2819}}.";
          type uint64;
          default "0";
        }
        leaf CRCErroredPackets {
          config false;
          description
          "This parameter is based on
          ''etherStatsCRCAlignErrors'' from {{bibref|RFC2819}}.";
          type uint32;
          default "0";
        }
        leaf UndersizePackets {
          config false;
          description
          "This parameter is based on
          ''etherStatsUndersizePkts'' from {{bibref|RFC2819}}.";
          type uint32;
          default "0";
        }
        leaf OversizePackets {
          config false;
          description
          "This parameter is based on ''etherStatsOversizePkts''
          from {{bibref|RFC2819}}.";
          type uint32;
          default "0";
        }
        leaf Packets64Bytes {
          config false;
          description
          "This parameter is based on ''etherStatsPkts64Octets''
          from {{bibref|RFC2819}}.";
          type uint64;
          default "0";
        }
        leaf Packets65to127Bytes {
          config false;
          description
          "This parameter is based on
          ''etherStatsPkts65to127Octets'' from
          {{bibref|RFC2819}}.";
          type uint64;
          default "0";
        }
        leaf Packets128to255Bytes {
          config false;
          description
          "This parameter is based on
          ''etherStatsPkts6128to255Octets'' from
          {{bibref|RFC2819}}.";
          type uint64;
          default "0";
        }
        leaf Packets256to511Bytes {
          config false;
          description
          "This parameter is based on
          ''etherStatsPkts256to511Octets'' from
          {{bibref|RFC2819}}.";
          type uint64;
          default "0";
        }
        leaf Packets512to1023Bytes {
          config false;
          description
          "This parameter is based on
          ''etherStatsPkts512to1023Octets'' from
          {{bibref|RFC2819}}.";
          type uint64;
          default "0";
        }
        leaf Packets1024to1518Bytes {
          config false;
          description
          "This parameter is based on
          ''etherStatsPkts1024to1518Octets'' from
          {{bibref|RFC2819}}.";
          type uint64;
          default "0";
        }
      }
      list LAG {
        key "MACAddress";
        unique "Alias";
        unique "Name";
        config true;
        description
        "Ethernet Link Aggregation Group (LAG) table (a
        stackable interface object as described in
        {{bibref|TR-181i2|Section 4.2}}). Table entries model
        the Link Aggregation Sub-Layer as defined in
        {{bibref|802.3-2015}} and {{bibref|802.1AX-2014}}. It
        is expected that a {{object}} interface can only be
        stacked above {{object|.Ethernet.Interface}}
        interfaces.  The CPE can reject creation of additional
        LAG instances if this would exceed its capabilities.";
        leaf Enable {
          config true;
          description
          "This parameter is based on ''ifAdminStatus'' from
          {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config false;
          description
          "The textual name of the LAG interface as assigned by
          the CPE.";
          type string {
            length "0..64";
          }
        }
        leaf LastChange {
          config false;
          description
          "The accumulated time in {{units}} since the interface
          entered its current operational state.";
          type uint32;
        }
        leaf-list LowerLayers {
          config true;
          description
          "For example, \"Device.Ethernet.Interface.1,
          Device.Ethernet.Interface.2\"";
          type string;
        }
        leaf MACAddress {
          config true;
          description
          "MAC address of the Link Aggregation Interface.";
          type yang:mac-address;
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type yang:counter32;
          }
          leaf BytesReceived {
            config false;
            description
            "The total number of bytes received on the
            interface, including framing characters.";
            type yang:counter32;
          }
          leaf PacketsSent {
            config false;
            description
            "The total number of packets transmitted out of the
            interface.";
            type yang:counter32;
          }
          leaf PacketsReceived {
            config false;
            description
            "The total number of packets received on the
            interface.";
            type yang:counter32;
          }
          leaf ErrorsSent {
            config false;
            description
            "The total number of outbound packets that could not
            be transmitted because of errors.";
            type yang:counter32;
          }
          leaf ErrorsReceived {
            config false;
            description
            "The total number of inbound packets that contained
            errors preventing them from being delivered to a
            higher-layer protocol.";
            type yang:counter32;
          }
          leaf UnicastPacketsSent {
            config false;
            description
            "The total number of packets requested for
            transmission which were not addressed to a
            multicast or broadcast address at this layer,
            including those that were discarded or not sent.";
            type yang:counter32;
          }
          leaf UnicastPacketsReceived {
            config false;
            description
            "The total number of received packets, delivered by
            this layer to a higher layer, which were not
            addressed to a multicast or broadcast address at
            this layer.";
            type yang:counter32;
          }
          leaf DiscardPacketsSent {
            config false;
            description
            "The total number of outbound packets which were
            chosen to be discarded even though no errors had
            been detected to prevent their being transmitted.
            One possible reason for discarding such a packet
            could be to free up buffer space.";
            type yang:counter32;
          }
          leaf DiscardPacketsReceived {
            config false;
            description
            "The total number of inbound packets which were
            chosen to be discarded even though no errors had
            been detected to  prevent their being delivered.
            One possible reason for discarding such a packet
            could be to free up buffer space.";
            type yang:counter32;
          }
          leaf MulticastPacketsSent {
            config false;
            description
            "The total number of packets that higher-level
            protocols requested for transmission and which were
            addressed to a multicast address at this layer,
            including those that were discarded or not sent.";
            type yang:counter32;
          }
          leaf MulticastPacketsReceived {
            config false;
            description
            "The total number of received packets, delivered by
            this layer to a higher layer, which were addressed
            to a multicast address at this layer.";
            type yang:counter32;
          }
          leaf BroadcastPacketsSent {
            config false;
            description
            "The total number of packets that higher-level
            protocols requested for transmission and which were
            addressed to a broadcast address at this layer,
            including those that were discarded or not sent.";
            type yang:counter32;
          }
          leaf BroadcastPacketsReceived {
            config false;
            description
            "The total number of received packets, delivered by
            this layer to a higher layer, which were addressed
            to a broadcast address at this layer.";
            type yang:counter32;
          }
          leaf UnknownProtoPacketsReceived {
            config false;
            description
            "The total number of packets received via the
            interface which were discarded because of an
            unknown or unsupported protocol.";
            type yang:counter32;
          }
        }
      }
    }
    container USB {
      description
      "Universal Serial Bus ({{bibref|USB1.0}},
      {{bibref|USB2.0}}, {{bibref|USB3.0}}). This object
      contains the {{object|Interface}}, {{object|Port}}, and
      {{object|USBHosts}} objects.";
      leaf InterfaceNumberOfEntries {
        config false;
        description
        "{{numentries}}";
        type uint32;
      }
      leaf PortNumberOfEntries {
        config false;
        description
        "{{numentries}}";
        type uint32;
      }
      list Interface {
        key "Name";
        unique "Alias";
        config true;
        description
        "USB interface table (a stackable interface object as
        described in {{bibref|TR-181i2|Section 4.2}}). This
        table models master and slave USB physical interfaces
        that support carrying Ethernet frames, e.g.  via the
        USB Communication Device Class.";
        leaf Enable {
          config true;
          description
          "This parameter is based on ''ifAdminStatus'' from
          {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config true;
          description
          "The textual name of the interface as assigned by the
          CPE.";
          type string {
            length "0..64";
          }
        }
        leaf LastChange {
          config false;
          description
          "The accumulated time in {{units}} since the interface
          entered its current operational state.";
          type uint32;
        }
        leaf-list LowerLayers {
          config true;
          description
          "Note: Since {{object}} is a layer 1 interface, it is
          expected that {{param}} will not be used.";
          type string;
        }
        leaf Upstream {
          config false;
          description
          "* For an End Device, {{param}} will be {{true}} for
          all interfaces.";
          type boolean;
        }
        leaf MACAddress {
          config false;
          description
          "Note: This is not necessarily the same as the
          Ethernet header source or destination MAC address,
          which is associated with the IP interface and is
          modeled via the
          {{param|.Ethernet.Link.{i}.MACAddress}} parameter.";
          type yang:mac-address;
        }
        leaf MaxBitRate {
          config false;
          description
          "The maximum PHY bit rate supported by this interface
          (expressed in {{units}}).";
          type uint32;
        }
        leaf Port {
          config false;
          description
          "{{reference}} This is the USB port associated with
          this interface object.";
          type string {
            length "0..256";
          }
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "The total number of packets that higher-level
            protocols requested for transmission and which were
            addressed to a broadcast address at this layer,
            including those that were discarded or not sent.";
            type uint64;
          }
          leaf BroadcastPacketsReceived {
            config false;
            description
            "The total number of received packets, delivered by
            this layer to a higher layer, which were addressed
            to a broadcast address at this layer.";
            type uint64;
          }
          leaf UnknownProtoPacketsReceived {
            config false;
            description
            "The total number of packets received via the
            interface which were discarded because of an
            unknown or unsupported  protocol.";
            type uint32;
          }
        }
      }
      list Port {
        key "Name";
        unique "Alias";
        config true;
        description
        "USB Port table.  This table models master and slave USB
        physical ports on the device.";
        leaf Alias {
          config true;
          description
          "{{datatype|expand}}";
          type Alias;
        }
        leaf Name {
          config true;
          description
          "The textual name of the port.";
          type string {
            length "0..64";
          }
        }
        leaf Standard {
          config false;
          description
          "USB specification version supported by the Port.
          Example: \"1.1\"";
          type string {
            length "0..4";
          }
        }
        leaf Type {
          config false;
          description
          "Type of the USB connection.";
          type enumeration {
            enum "Host";
            enum "Hub";
            enum "Device";
          }
        }
        leaf Receptacle {
          config false;
          description
          "Receptacle of the port.";
          type enumeration {
            enum "Standard-A";
            enum "Standard-B";
            enum "Powered-B";
            enum "Micro-AB";
            enum "Micro-B";
          }
        }
        leaf Rate {
          config false;
          description
          "Current speed of the USB connection.  {{enum}}";
          type enumeration {
            enum "Low" {
              description
              "1.5 Mbits/sec (187.5 KB/sec) defined in
              {{bibref|USB1.0}}";
            }
            enum "Full" {
              description
              "12 Mbits/sec (1.5 MB/sec) defined in
              {{bibref|USB1.0}}";
            }
            enum "High" {
              description
              "480 Mbits/sec (60 MB/sec) defined in
              {{bibref|USB2.0}}";
            }
            enum "Super" {
              description
              "5.0 Gbits/sec (625 MB/sec) defined in
              {{bibref|USB3.0}}";
            }
          }
        }
        leaf Power {
          config false;
          description
          "Only applies when {{param|Type}} is
          {{enum|Device|Type}}. In other cases value is
          {{enum|Unknown}}.";
          type enumeration {
            enum "Self";
            enum "Bus";
            enum "Unknown";
          }
        }
      }
      container USBHosts {
        description
        "See {{bibref|TR-157|Appendix I}} for Theory of
        Operation.";
        leaf HostNumberOfEntries {
          config false;
          description
          "{{numentries}}";
          type uint32;
        }
        list Host {
          key "Name";
          unique "Alias";
          config true;
          description
          "Table of CPE USB Host controllers.";
          leaf Alias {
            config true;
            description
            "{{datatype|expand}}";
            type Alias;
          }
          leaf Enable {
            config true;
            description
            "Enables or disables the USB Host controller.";
            type boolean;
          }
          leaf Name {
            config true;
            description
            "User-readable host controller name.";
            type string {
              length "0..64";
            }
          }
          leaf Type {
            config false;
            description
            "Type of USB Host";
            type enumeration {
              enum "OHCI" {
                description
                "Open Host Controller Interface";
              }
              enum "EHCI" {
                description
                "Enhanced Host Controller Interface";
              }
              enum "UHCI" {
                description
                "Universal Host Controller Interface";
              }
              enum "xHCI" {
                description
                "Extensible Host Controller Interface";
              }
            }
          }
          leaf Reset {
            config true;
            description
            "The value is not saved in the device's state and
            setting it to {{false}} has no effect.";
            type boolean;
          }
          leaf PowerManagementEnable {
            config true;
            description
            "When set to {{false}} {{param}} immediately
            disables the Host controller Power Management
            policy.";
            type boolean;
          }
          leaf USBVersion {
            config false;
            description
            "USB specification version with which the controller
            complies.  Example: \"1.1\"";
            type string {
              length "0..4";
            }
          }
          leaf DeviceNumberOfEntries {
            config false;
            description
            "{{numentries}}";
            type uint32;
          }
          list Device {
            key "DeviceNumber";
            config false;
            description
            "Table of connected USB devices.";
            leaf DeviceNumber {
              config false;
              description
              "Device number on USB bus.";
              type uint32;
            }
            leaf USBVersion {
              config false;
              description
              "USB specification version with which the device
              complies.  Example: \"1.1\"";
              type string {
                length "0..4";
              }
            }
            leaf DeviceClass {
              config false;
              description
              "When 0x00, each device specifies its own class
              code.  When 0xFF, the class code is vendor
              specified.";
              type yang:hex-string {
                length "0..1";
              }
            }
            leaf DeviceSubClass {
              config false;
              description
              "Subclass code (assigned by USB-IF).";
              type yang:hex-string {
                length "0..1";
              }
            }
            leaf DeviceVersion {
              config false;
              description
              "Device release number.";
              type uint32 {
                range "min..65535";
              }
            }
            leaf DeviceProtocol {
              config false;
              description
              "Protocol code (assigned by USB-IF).";
              type yang:hex-string {
                length "0..1";
              }
            }
            leaf ProductID {
              config false;
              description
              "Product ID (assigned by manufacturer).";
              type uint32 {
                range "min..65535";
              }
            }
            leaf VendorID {
              config false;
              description
              "Vendor ID (assigned by USB-IF).";
              type uint32 {
                range "min..65535";
              }
            }
            leaf Manufacturer {
              config false;
              description
              "Device Manufacturer string descriptor.";
              type string {
                length "0..64";
              }
            }
            leaf ProductClass {
              config false;
              description
              "Device Product Class string descriptor.";
              type string {
                length "0..64";
              }
            }
            leaf SerialNumber {
              config false;
              description
              "Device SerialNumber string descriptor.";
              type string {
                length "0..64";
              }
            }
            leaf Port {
              config false;
              description
              "0 when no parent.";
              type uint32 {
                range "min..255";
              }
            }
            leaf USBPort {
              config false;
              description
              "{{reference}} This is a reference to the USB host
              device to which this (external) USB device is
              connected.";
              type string;
            }
            leaf Rate {
              config false;
              description
              "Internal signaling between the connected USB
              device and the USB Host Controller provide the
              information needed to determine the negotiated
              rate.";
              type enumeration {
                enum "Low" {
                  description
                  "1.5 Mbits/sec (187.5 KB/sec) defined in
                  {{bibref|USB1.0}}";
                }
                enum "Full" {
                  description
                  "12 Mbits/sec (1.5 MB/sec) defined in
                  {{bibref|USB1.0}}";
                }
                enum "High" {
                  description
                  "480 Mbits/sec (60 MB/sec) defined in
                  {{bibref|USB2.0}}";
                }
                enum "Super" {
                  description
                  "5.0 Gbits/sec (625 MB/sec) defined in
                  {{bibref|USB3.0}}";
                }
              }
            }
            leaf Parent {
              config false;
              description
              "This is {{empty}} for a device connected to the
              Host controller (root hub).";
              type string;
            }
            leaf MaxChildren {
              config false;
              description
              "Number of ports.  Only applies for hub device,
              equal to 0 for other devices.";
              type uint32;
            }
            leaf IsSuspended {
              config false;
              description
              "When {{false}} the associated Device is in any of
              the other states specified by the USB 2.0 Device
              State Machine (see {{bibref|USB2.0|Chapter
              9.1.1}}).";
              type boolean;
            }
            leaf IsSelfPowered {
              config false;
              description
              "When {{false}} the associated device draws all
              the current it needs from the USB bus.";
              type boolean;
            }
            leaf ConfigurationNumberOfEntries {
              config false;
              description
              "{{numentries}}";
              type uint32;
            }
            list Configuration {
              key "ConfigurationNumber";
              config false;
              description
              "Table of device configurations.";
              leaf ConfigurationNumber {
                config false;
                description
                "The identifier for each Device Configuration.";
                type uint32;
              }
              leaf InterfaceNumberOfEntries {
                config false;
                description
                "{{numentries}}";
                type uint32;
              }
              list Interface {
                key "InterfaceNumber";
                config false;
                description
                "Table of device interface descriptors.";
                leaf InterfaceNumber {
                  config false;
                  description
                  "Number of this interface (from USB interface
                  descriptor).";
                  type uint32 {
                    range "min..255";
                  }
                }
                leaf InterfaceClass {
                  config false;
                  description
                  "When 0x00, each interface specifies its own
                  class code.  When 0xFF, the class code is
                  vendor specified.";
                  type yang:hex-string {
                    length "0..1";
                  }
                }
                leaf InterfaceSubClass {
                  config false;
                  description
                  "Subclass code (assigned by USB-IF).";
                  type yang:hex-string {
                    length "0..1";
                  }
                }
                leaf InterfaceProtocol {
                  config false;
                  description
                  "Protocol code (assigned by USB-IF).";
                  type yang:hex-string {
                    length "0..1";
                  }
                }
              }
            }
          }
        }
      }
    }
    container HPNA {
      description
      "HPNA object that contains the {{object|Interface}} and
      {{object|Diagnostics}} objects.  The HPNA (also known as
      HomePNA) industry standard {{bibref|G.9954}} defines peer
      to peer communication for home networking over existing
      coax cables and telephone wiring within the home.";
      leaf InterfaceNumberOfEntries {
        config false;
        description
        "{{numentries}}";
        type uint32;
      }
      list Interface {
        key "Name";
        unique "Alias";
        config true;
        description
        "HPNA interface table (a stackable interface object as
        described in {{bibref|TR-181i2|Section 4.2}}). Each
        table entry models the PHY and MAC levels of an HPNA
        interface {{bibref|G.9954}}.";
        leaf Enable {
          config true;
          description
          "This parameter is based on ''ifAdminStatus'' from
          {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config true;
          description
          "The textual name of the interface as assigned by the
          CPE.";
          type string {
            length "0..64";
          }
        }
        leaf LastChange {
          config false;
          description
          "The accumulated time in {{units}} since the interface
          entered its current operational state.";
          type uint32;
        }
        leaf-list LowerLayers {
          config true;
          description
          "Note: Since {{object}} is a layer 1 interface, it is
          expected that {{param}} will not be used.";
          type string;
        }
        leaf Upstream {
          config false;
          description
          "* For an End Device, {{param}} will be {{true}} for
          all interfaces.";
          type boolean;
        }
        leaf MACAddress {
          config false;
          description
          "Note: This is not necessarily the same as the
          Ethernet header source or destination MAC address,
          which is associated with the IP interface and is
          modeled via the
          {{param|.Ethernet.Link.{i}.MACAddress}} parameter.";
          type yang:mac-address;
        }
        leaf FirmwareVersion {
          config false;
          description
          "This interface's firmware version.";
          type string {
            length "0..64";
          }
        }
        leaf NodeID {
          config false;
          description
          "The Node ID of this interface.";
          type uint32;
        }
        leaf IsMaster {
          config false;
          description
          "Whether this interface is the HPNA network master.";
          type boolean;
        }
        leaf Synced {
          config false;
          description
          "Whether this interface is synchronized with the HPNA
          network master.  If this interface is the HPNA
          network master, {{param}} MUST be {{true}}.";
          type boolean;
        }
        leaf TotalSyncTime {
          config false;
          description
          "Total time in {{units}} (since device reset) that
          this interface has been up and synchronized to the
          HPNA network master.";
          type uint32;
        }
        leaf MaxBitRate {
          config false;
          description
          "The maximum HPNA PHY bit rate (expressed in
          {{units}}) of this interface.";
          type uint32;
        }
        leaf NetworkUtilization {
          config false;
          description
          "Current HPNA network utilization (expressed in
          {{units}}).";
          type uint32 {
            range "0..1000";
          }
        }
        leaf-list PossibleConnectionTypes {
          config false;
          description
          "{{list}} List items indicate the types of connections
          possible for this interface.  {{enum}}";
          type enumeration {
            enum "Phone";
            enum "Coax";
          }
        }
        leaf-list ConnectionType {
          config true;
          description
          "{{list}} Connection type(s) for which the HPNA
          protocol is active.";
          type string;
          must ". = ../PossibleConnectionTypes";
        }
        leaf-list PossibleSpectralModes {
          config false;
          description
          "{{list}} List items indicate the spectral modes
          possible for this interface.  {{enum}}";
          type enumeration {
            enum "A" {
              description
              "4-20MHz - Phone / Coax";
            }
            enum "B" {
              description
              "12-28MHz - Phone / Coax";
            }
            enum "C" {
              description
              "36-52MHz - Coax only";
            }
            enum "D" {
              description
              "4-36MHz - Coax only";
            }
          }
        }
        leaf SpectralMode {
          config true;
          description
          "Spectral mode for which the HPNA protocol is active.";
          type string;
          must ". = ../PossibleSpectralModes";
        }
        leaf MTU {
          config true;
          description
          "Maximum Transmission Unit for this HPNA interface
          (expressed in {{units}}).";
          type uint32;
        }
        leaf NoiseMargin {
          config true;
          description
          "The desired noise margin for which the local HPNA
          interface has been configured (expressed in
          {{units}}).";
          type uint32;
        }
        leaf DefaultNonLARQPER {
          config true;
          description
          "The desired packet error rate for which the local
          HPNA interface has been configured (expressed in
          1E-8, e.g.  PER of 1.27E-6 will be presented as 127).";
          type uint32;
        }
        leaf LARQEnable {
          config true;
          description
          "Enable or disable the Limited Automatic Repeat
          Request (LARQ) mechanism.";
          type boolean;
        }
        leaf MinMulticastRate {
          config true;
          description
          "The minimum multicast (and broadcast) rate that can
          be negotiated on the HPNA network directly accessible
          via this interface (expressed in {{units}}).";
          type uint32;
        }
        leaf NegMulticastRate {
          config false;
          description
          "The negotiated multicast (and broadcast) rate on the
          HPNA network directly accessible via this interface
          (expressed in {{units}}).";
          type uint32;
        }
        leaf MasterSelectionMode {
          config true;
          description
          "Master selection mode.  {{enum}}";
          type enumeration {
            enum "Automatic" {
              description
              "Automatic master selection";
            }
            enum "ForceEndpoint" {
              description
              "Force local HPNA interface to be end point";
            }
            enum "ForceMaster" {
              description
              "Force local HPNA interface to be master";
            }
          }
        }
        leaf AssociatedDeviceNumberOfEntries {
          config false;
          description
          "{{numentries}} This is the number of HPNA nodes that
          are directly accessible via this interface.";
          type uint32;
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "The total number of packets that higher-level
            protocols requested for transmission and which were
            addressed to a broadcast address at this layer,
            including those that were discarded or not sent.";
            type uint64;
          }
          leaf BroadcastPacketsReceived {
            config false;
            description
            "The total number of received packets, delivered by
            this layer to a higher layer, which were addressed
            to a broadcast address at this layer.";
            type uint64;
          }
          leaf UnknownProtoPacketsReceived {
            config false;
            description
            "The total number of packets received via the
            interface which were discarded because of an
            unknown or unsupported  protocol.";
            type uint32;
          }
        }
        container QoS {
          description
          "QoS configuration object.";
          leaf FlowSpecNumberOfEntries {
            config false;
            description
            "{{numentries}}";
            type uint32;
          }
          list FlowSpec {
            key "Alias";
            config true;
            description
            "For enabled table entries, if
            {{param|TrafficClasses}} is {{empty}} then the
            table entry is inoperable and the CPE MUST set
            {{param|Status}} to
            {{enum|Error_Misconfigured|Status}}.";
            leaf Enable {
              config true;
              description
              "Enables or disables the table entry.";
              type boolean;
              default "false";
            }
            leaf Status {
              config false;
              description
              "The {{enum|Error}} value MAY be used by the CPE
              to indicate a locally defined error condition.";
              type enumeration {
                enum "Disabled";
                enum "Enabled";
                enum "Error_Misconfigured";
                enum "Error";
              }
              default "Disabled";
            }
            leaf Alias {
              config true;
              description
              "{{datatype|expand}}";
              type Alias;
            }
            leaf-list TrafficClasses {
              config true;
              description
              "{{list}} This list identifies the set of traffic
              classes associated with this flow spec.";
              type uint32;
            }
            leaf FlowType {
              config true;
              description
              "Flow type.  {{enum}}";
              type enumeration {
                enum "CBR" {
                  description
                  "Constant Bit Rate";
                }
                enum "VBR" {
                  description
                  "Variable Bit Rate";
                }
                enum "VBR-NRT" {
                  description
                  "Variable Bit Rate - Non Real Time";
                }
                enum "BE" {
                  description
                  "Best Effort";
                }
              }
              default "BE";
            }
            leaf Priority {
              config true;
              description
              "Priority 0 is the lowest priority.";
              type uint32 {
                range "0..7";
              }
              default "0";
            }
            leaf Latency {
              config true;
              description
              "Value 0 means no latency requirements.";
              type uint32 {
                range "0..999";
              }
              default "0";
            }
            leaf Jitter {
              config true;
              description
              "Value 0 means no jitter requirements.";
              type uint32 {
                range "0..999";
              }
              default "0";
            }
            leaf PacketSize {
              config true;
              description
              "Value 0 means undefined packet size.";
              type uint32 {
                range "0..max";
              }
              default "0";
            }
            leaf MinRate {
              config true;
              description
              "Value 0 means no MinRate requirements.";
              type uint32;
              default "0";
            }
            leaf AvgRate {
              config true;
              description
              "Value 0 means no AvgRate requirements.";
              type uint32;
              default "0";
            }
            leaf MaxRate {
              config true;
              description
              "Value 0 means no MaxRate requirements.";
              type uint32;
              default "0";
            }
            leaf PER {
              config true;
              description
              "Value 0 means no PER requirements.";
              type uint32;
              default "0";
            }
            leaf Timeout {
              config true;
              description
              "Value 0 means unlimited timeout.";
              type uint32;
              default "0";
            }
          }
        }
        list AssociatedDevice {
          key "MACAddress";
          config true;
          description
          "This table provides information about other HPNA
          devices that are directly accessible via this HPNA
          interface.";
          leaf MACAddress {
            config true;
            description
            "The physical address of this node.";
            type yang:mac-address;
          }
          leaf NodeID {
            config false;
            description
            "The Node ID of this node.";
            type uint32;
          }
          leaf IsMaster {
            config false;
            description
            "Whether this node is the HPNA network master.";
            type boolean;
          }
          leaf Synced {
            config false;
            description
            "Whether this node is synchronized with the HPNA
            network master.  If this node is the HPNA network
            master, {{param}} MUST be {{true}}.";
            type boolean;
          }
          leaf TotalSyncTime {
            config false;
            description
            "Total time in {{units}} (since device reset) that
            this node has been up and synchronized to the HPNA
            network master.";
            type uint32;
          }
          leaf MaxBitRate {
            config false;
            description
            "This node's maximum HPNA PHY bit rate (expressed in
            {{units}}).";
            type uint32;
          }
          leaf PHYDiagnosticsEnable {
            config true;
            description
            "Enable / disable PHY throughput diagnostics mode on
            this node.  All devices that are enabled will
            participate in the HPNA network PHY throughput
            diagnostics process.";
            type boolean;
          }
          leaf Active {
            config false;
            description
            "The ability to list inactive nodes is OPTIONAL.  If
            the CPE includes inactive nodes in this table,
            {{param}} MUST be set to {{false}}  for each
            inactive node.  The length of time an inactive node
            remains listed in this table is a local matter to
            the CPE.";
            type boolean;
          }
        }
      }
      container Diagnostics {
        description
        "The HPNA Diagnostics object.";
        container PHYThroughput {
          description
          "When diagnostics are requested, all HPNA nodes for
          which the
          {{param|##.Interface.{i}.AssociatedDevice.{i}.PHYDiagnosticsEnable}}
          parameter is set enter PHY diagnostics  mode.";
          leaf DiagnosticsState {
            config true;
            description
            "{{datatype|expand}}";
            type DiagnosticsState;
          }
          leaf Interface {
            config true;
            description
            "{{reference}}  This is the interface over which the
            test is to be performed.";
            type string {
              length "0..256";
            }
          }
          leaf NumPacketsInBurst {
            config true;
            description
            "Number of test packet in burst to be send during
            PHY diagnostics test from each HPNA device to other
            HPNA device  in the HPNA network.";
            type uint32;
          }
          leaf BurstInterval {
            config true;
            description
            "Test packet burst interval length (expressed in
            {{units}}).";
            type uint32;
          }
          leaf TestPacketPayloadLength {
            config true;
            description
            "Payload length in the test packets.";
            type uint32 {
              range "0..1480";
            }
          }
          leaf PayloadEncoding {
            config true;
            description
            "HPNA payload encoding in PHY diagnostics.  0 is
            used for negotiated payload between devices
            according to line  conditions.";
            type uint32;
          }
          leaf PayloadDataGen {
            config true;
            description
            "Test packets payload data generator value.";
            type uint32;
          }
          leaf PayloadType {
            config true;
            description
            "In IncrementByte mode LSByte in PayloadDataGen is
            used as first payload  and next bytes in payload
            are incremented.";
            type enumeration {
              enum "Pattern";
              enum "IncrementByte";
            }
          }
          leaf PriorityLevel {
            config true;
            description
            "Priority level of PHY diagnostics packets (0 lowest
            -7 highest).";
            type uint32 {
              range "0..7";
            }
          }
          leaf ResultNumberOfEntries {
            config false;
            description
            "{{numentries}} This is the number of PHY
            diagnostics results.";
            type uint32;
          }
          list Result {
            key "SrcMACAddress DestMACAddress";
            config false;
            description
            "Each result object corresponds to unidirectional
            traffic between two PHY diagnostics-enabled nodes
            (so there are two such objects for  each such
            pair).";
            leaf SrcMACAddress {
              config false;
              description
              "HPNA source MAC address.";
              type yang:mac-address;
            }
            leaf DestMACAddress {
              config false;
              description
              "HPNA destination MAC address.";
              type yang:mac-address;
            }
            leaf PHYRate {
              config false;
              description
              "PHY diagnostics HPNA PHY rate (expressed in
              {{units}}).";
              type uint32;
            }
            leaf BaudRate {
              config false;
              description
              "PHY Baud rate (expressed in {{units}}).";
              type uint32;
            }
            leaf SNR {
              config false;
              description
              "PHY diagnostics SNR (expressed in {{units}}).";
              type uint32;
            }
            leaf PacketsReceived {
              config false;
              description
              "Number of received packets in PHY diagnostics
              mode.";
              type uint32;
            }
            leaf Attenuation {
              config false;
              description
              "Measured attenuation (expressed in {{units}}).";
              type uint32;
            }
          }
        }
        container PerformanceMonitoring {
          description
          "Performance monitoring results are sampled from all
          nodes in the HPNA network.  All packet related
          counters are sampled synchronized at all nodes in the
          HPNA network in order to derive packet loss
          calculations in the HPNA network.";
          leaf DiagnosticsState {
            config true;
            description
            "{{datatype|expand}}";
            type DiagnosticsState;
          }
          leaf Interface {
            config true;
            description
            "{{reference}} This is the interface over which the
            test is to be performed.";
            type string {
              length "0..256";
            }
          }
          leaf SampleInterval {
            config true;
            description
            "If SampleInterval is a simple fraction of a day,
            e.g.  900 (a quarter of an hour) or 3600 (an hour),
            the CPE MAY choose to align sample intervals with
            time of day, but is not required to do so.";
            type uint32;
          }
          container Nodes {
            description
            "Note: Packets in statistics counters are Ethernet
            packets.";
            leaf CurrentStart {
              config false;
              description
              "When automatic collection is disabled, i.e.
              SampleInterval is zero, the current interval
              started two manual samples  ago.";
              type yang:date-and-time;
            }
            leaf CurrentEnd {
              config false;
              description
              "When automatic collection is disabled, i.e.
              SampleInterval is zero, the current interval
              ended at the most recent manual  sample.";
              type yang:date-and-time;
            }
            leaf NodeNumberOfEntries {
              config false;
              description
              "{{numentries}} This is the number of HPNA nodes
              for which performance monitoring results were
              collected during the current sample interval.";
              type uint32;
            }
            list Node {
              key "MACAddress";
              config false;
              description
              "Note: Packet counters indicate the number of
              packets received between {{param|#.CurrentStart}}
              and {{param|#.CurrentEnd}}.";
              leaf MACAddress {
                config false;
                description
                "The MAC address of the HPNA node.";
                type yang:mac-address;
              }
              leaf BytesSent {
                config false;
                description
                "The total number of bytes sent by host
                equipment for transmission on the HPNA
                interface.";
                type uint64;
              }
              leaf BytesReceived {
                config false;
                description
                "The total number of received bytes on the HPNA
                interface destined for the host equipment.";
                type uint64;
              }
              leaf PacketsSent {
                config false;
                description
                "The total number of packets sent by host
                equipment for transmission on the HPNA
                interface.  Number includes also short error
                packets and control packets.";
                type uint64;
              }
              leaf PacketsReceived {
                config false;
                description
                "The total number of good packets received on
                the HPNA interface destined for the host
                equipment.";
                type uint64;
              }
              leaf BroadcastPacketsSent {
                config false;
                description
                "The number of broadcast packets transmitted on
                the HPNA interface.";
                type uint64;
              }
              leaf BroadcastPacketsReceived {
                config false;
                description
                "The number of broadcast packets received on the
                HPNA interface.";
                type uint64;
              }
              leaf MulticastPacketsSent {
                config false;
                description
                "The number of multicast packets transmitted on
                the HPNA interface.";
                type uint64;
              }
              leaf MulticastPacketsReceived {
                config false;
                description
                "The number of multicast packets received on the
                HPNA interface.";
                type uint64;
              }
              leaf PacketsCrcErrored {
                config false;
                description
                "The number of packets received on the HPNA
                interface with CRC errors.";
                type uint32;
              }
              leaf PacketsCrcErroredHost {
                config false;
                description
                "The number of CRC error packets received on the
                HPNA interface destined for the host equipment.";
                type uint32;
              }
              leaf PacketsShortErrored {
                config false;
                description
                "The number of packets received on the HPNA
                interface that are too short to be valid.";
                type uint32;
              }
              leaf PacketsShortErroredHost {
                config false;
                description
                "The number packets sent by the host equipment
                that are too short to be valid.";
                type uint32;
              }
              leaf RxPacketsDropped {
                config false;
                description
                "The number of received packets dropped due to
                lack of resources.";
                type uint32;
              }
              leaf TxPacketsDropped {
                config false;
                description
                "The number packets sent by the host equipment
                for transmission on the HPNA interface but
                dropped due to lack of resources.";
                type uint32;
              }
              leaf ControlRequestLocal {
                config false;
                description
                "The number of HPNA control request packets from
                local host.";
                type uint32;
              }
              leaf ControlReplyLocal {
                config false;
                description
                "The number of HPNA control reply packets to
                local host.";
                type uint32;
              }
              leaf ControlRequestRemote {
                config false;
                description
                "The number of HPNA control request packets from
                remote host.";
                type uint32;
              }
              leaf ControlReplyRemote {
                config false;
                description
                "The number of HPNA control reply packets to
                remote host.";
                type uint32;
              }
              leaf PacketsSentWire {
                config false;
                description
                "The total number of packets transmitted to
                wire.";
                type uint64;
              }
              leaf BroadcastPacketsSentWire {
                config false;
                description
                "The total number of broadcast packets
                transmitted to wire.";
                type uint64;
              }
              leaf MulticastPacketsSentWire {
                config false;
                description
                "The total number of multicast packets
                transmitted to wire.";
                type uint64;
              }
              leaf PacketsInternalControl {
                config false;
                description
                "The number of HPNA control request packets from
                internal node.";
                type uint32;
              }
              leaf BroadcastPacketsInternalControl {
                config false;
                description
                "The number of HPNA broadcast control request
                packets from internal node.";
                type uint32;
              }
              leaf PacketsReceivedQueued {
                config false;
                description
                "The number of received packets queued on host
                output queues.";
                type uint32;
              }
              leaf PacketsReceivedForwardUnknown {
                config false;
                description
                "The number of packets received and forwarded to
                unknown hosts.";
                type uint32;
              }
              leaf NodeUtilization {
                config false;
                description
                "The node utilization (expressed in {{units}}).";
                type uint32 {
                  range "0..1000";
                }
              }
            }
          }
          container Channels {
            description
            "Note: channels are unidirectional.";
            leaf TimeStamp {
              config false;
              description
              "Time at which channel data was last collected.";
              type yang:date-and-time;
            }
            leaf ChannelNumberOfEntries {
              config false;
              description
              "{{numentries}} This is the number of HPNA
              channels for which performance monitoring results
              have been collected.";
              type uint32;
            }
            list Channel {
              key "HostSrcMACAddress HostDestMACAddress";
              config false;
              description
              "Per-channel HPNA performance monitoring results.";
              leaf HostSrcMACAddress {
                config false;
                description
                "The host source MAC address associated with the
                channel.";
                type yang:mac-address;
              }
              leaf HostDestMACAddress {
                config false;
                description
                "The host destination MAC address associated
                with the channel.";
                type yang:mac-address;
              }
              leaf HPNASrcMACAddress {
                config false;
                description
                "The HPNA source MAC address associated with the
                channel.";
                type yang:mac-address;
              }
              leaf HPNADestMACAddress {
                config false;
                description
                "The HPNA destination MAC address associated
                with the channel.";
                type yang:mac-address;
              }
              leaf PHYRate {
                config false;
                description
                "Channel PHY rate (expressed in {{units}}).";
                type uint32;
              }
              leaf BaudRate {
                config false;
                description
                "PHY Baud rate (expressed in {{units}}).";
                type uint32;
              }
              leaf SNR {
                config false;
                description
                "Channel actual SNR measured in receiver side
                (expressed in {{units}}).";
                type uint32;
              }
              leaf PacketsSent {
                config false;
                description
                "Number of packets sent in the channel.";
                type uint32;
              }
              leaf PacketsReceived {
                config false;
                description
                "Pre-LARQ number of packets received in the
                channel.";
                type uint32;
              }
              leaf LARQPacketsReceived {
                config false;
                description
                "Post-LARQ number of packets received in the
                channel.  Valid only if LARQ is enabled.";
                type uint32;
              }
              leaf FlowSpec {
                config false;
                description
                "{{null}} means that the channel is not
                associated with any specified flow
                specification in the QoS object.";
                type string {
                  length "0..256";
                }
              }
            }
          }
        }
      }
    }
    container MoCA {
      description
      "MoCA object that contains the {{object|Interface}} table
      {{bibref|MoCAv1.0}} {{bibref|MoCAv1.1}}.";
      leaf InterfaceNumberOfEntries {
        config false;
        description
        "{{numentries}}";
        type uint32;
      }
      list Interface {
        key "Name";
        unique "Alias";
        config true;
        description
        "MoCA interface table (a stackable interface object as
        described in {{bibref|TR-181i2|Section 4.2}}). Each
        table entry models the PHY and MAC levels of a MoCA
        interface {{bibref|MoCAv1.0}} {{bibref|MoCAv1.1}}.";
        leaf Enable {
          config true;
          description
          "This parameter is based on ''ifAdminStatus'' from
          {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config true;
          description
          "The textual name of the interface as assigned by the
          CPE.";
          type string {
            length "0..64";
          }
        }
        leaf LastChange {
          config false;
          description
          "The accumulated time in {{units}} since the interface
          entered its current operational state.";
          type uint32;
        }
        leaf-list LowerLayers {
          config true;
          description
          "Note: Since {{object}} is a layer 1 interface, it is
          expected that {{param}} will not be used.";
          type string;
        }
        leaf Upstream {
          config false;
          description
          "* For an End Device, {{param}} will be {{true}} for
          all interfaces.";
          type boolean;
        }
        leaf MACAddress {
          config false;
          description
          "Note: This is not necessarily the same as the
          Ethernet header source or destination MAC address,
          which is associated with the IP interface and is
          modeled via the
          {{param|.Ethernet.Link.{i}.MACAddress}} parameter.";
          type yang:mac-address;
        }
        leaf FirmwareVersion {
          config false;
          description
          "This parameter is based on ''mocaIfSoftwareVersion''
          from {{bibref|MOCA11-MIB}}.";
          type string {
            length "0..64";
          }
        }
        leaf MaxBitRate {
          config false;
          description
          "The maximum MoCA PHY bit rate (expressed in
          {{units}}).";
          type uint32;
        }
        leaf MaxIngressBW {
          config false;
          description
          "This parameter is based on ''mocaIfMaxIngressNodeBw''
          from {{bibref|MOCA11-MIB}}.";
          type uint32;
        }
        leaf MaxEgressBW {
          config false;
          description
          "This parameter is based on ''mocaIfMaxEgressNodeBw''
          from {{bibref|MOCA11-MIB}}.";
          type uint32;
        }
        leaf HighestVersion {
          config false;
          description
          "This parameter is based on ''mocaIfMocaVersion'' from
          {{bibref|MOCA11-MIB}}.";
          type string {
            length "0..64";
            pattern "\\d+(\\.\\d+)*";
          }
        }
        leaf CurrentVersion {
          config false;
          description
          "This parameter is based on ''mocaIfNetworkVersion''
          from {{bibref|MOCA11-MIB}}.";
          type string {
            length "0..64";
            pattern "\\d+(\\.\\d+)*";
          }
        }
        leaf NetworkCoordinator {
          config false;
          description
          "This parameter is based on ''mocaIfNC'' from
          {{bibref|MOCA11-MIB}}.";
          type uint32;
        }
        leaf NodeID {
          config false;
          description
          "This parameter is based on ''mocaIfNodeID'' from
          {{bibref|MOCA11-MIB}}.";
          type uint32;
        }
        leaf MaxNodes {
          config false;
          description
          "The maximum network node capability supported by the
          interface.  If {{param}} is {{true}} then the
          interface supports 16 nodes (the maximum for a MoCA
          1.1 network). If {{param}} is false then the
          interface supports 8 nodes (the maximum for a MoCA
          1.0 network).";
          type boolean;
        }
        leaf PreferredNC {
          config true;
          description
          "This parameter is based on ''mocaIfPreferredNC'' from
          {{bibref|MOCA11-MIB}}.";
          type boolean;
        }
        leaf BackupNC {
          config false;
          description
          "This parameter is based on ''mocaIfBackupNC'' from
          {{bibref|MOCA11-MIB}}.";
          type uint32;
        }
        leaf PrivacyEnabledSetting {
          config true;
          description
          "The configured privacy setting MAY NOT match the
          current operational state ({{param|PrivacyEnabled}}),
          since this setting is only applied during network
          formation or admission.";
          type boolean;
        }
        leaf PrivacyEnabled {
          config false;
          description
          "This parameter is based on ''mocaIfPrivacyEnable''
          from {{bibref|MOCA11-MIB}}.";
          type boolean;
        }
        leaf FreqCapabilityMask {
          config false;
          description
          "This parameter is based on ''mocaIfCapabilityMask''
          from {{bibref|MOCA11-MIB}}.";
          type yang:hex-string {
            length "8";
          }
        }
        leaf FreqCurrentMaskSetting {
          config true;
          description
          "The configured frequencies MAY NOT match the current
          operational state ({{param|FreqCurrentMask}}), since
          this setting is only applied during network formation
          or admission.";
          type yang:hex-string {
            length "8";
          }
        }
        leaf FreqCurrentMask {
          config false;
          description
          "This parameter is based on ''mocaIfChannelMask'' from
          {{bibref|MOCA11-MIB}}.";
          type yang:hex-string {
            length "8";
          }
        }
        leaf CurrentOperFreq {
          config false;
          description
          "This parameter is based on ''mocaIfRFChannel'' from
          {{bibref|MOCA11-MIB}}.";
          type uint32;
        }
        leaf LastOperFreq {
          config false;
          description
          "This parameter is based on ''mocaIfLOF'' from
          {{bibref|MOCA11-MIB}}.";
          type uint32;
        }
        leaf KeyPassphrase {
          config true;
          description
          "This parameter is based on ''mocaIfPassword'' from
          {{bibref|MOCA11-MIB}}.";
          type string {
            length "12..17";
            pattern "\\d+";
          }
        }
        leaf TxPowerLimit {
          config true;
          description
          "This parameter is based on ''mocaIfTxPowerLimit''
          from {{bibref|MOCA11-MIB}}.";
          type uint32;
        }
        leaf PowerCntlPhyTarget {
          config true;
          description
          "This parameter is based on
          ''mocaIfPowerControlTargetRate'' from
          {{bibref|MOCA11-MIB}}.";
          type uint32;
        }
        leaf BeaconPowerLimit {
          config true;
          description
          "This parameter is based on ''mocaIfBeaconPowerLimit''
          from {{bibref|MOCA11-MIB}}.";
          type uint32;
        }
        leaf NetworkTabooMask {
          config false;
          description
          "This parameter is based on ''mocaIfTabooChannelMask''
          from {{bibref|MOCA11-MIB}}.";
          type yang:hex-string {
            length "8";
          }
        }
        leaf NodeTabooMask {
          config false;
          description
          "This parameter is based on
          ''mocaIfNodeTabooChannelMask'' from
          {{bibref|MOCA11-MIB}}.";
          type yang:hex-string {
            length "8";
          }
        }
        leaf TxBcastRate {
          config false;
          description
          "This parameter is based on ''mocaIfTxGcdRate'' from
          {{bibref|MOCA11-MIB}}.";
          type uint32;
        }
        leaf TxBcastPowerReduction {
          config false;
          description
          "This parameter is based on
          ''mocaIfTxGcdPowerReduction'' from
          {{bibref|MOCA11-MIB}}.";
          type uint32;
        }
        leaf QAM256Capable {
          config false;
          description
          "This parameter is based on ''mocaIfQAM256Capable''
          from {{bibref|MOCA11-MIB}}.";
          type boolean;
        }
        leaf PacketAggregationCapability {
          config false;
          description
          "This parameter is based on
          ''mocaIfPacketsAggrCapability'' from
          {{bibref|MOCA11-MIB}}.";
          type uint32 {
            range "0..10";
          }
        }
        leaf AssociatedDeviceNumberOfEntries {
          config false;
          description
          "{{numentries}}";
          type uint32;
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "The total number of packets that higher-level
            protocols requested for transmission and which were
            addressed to a broadcast address at this layer,
            including those that were discarded or not sent.";
            type uint64;
          }
          leaf BroadcastPacketsReceived {
            config false;
            description
            "The total number of received packets, delivered by
            this layer to a higher layer, which were addressed
            to a broadcast address at this layer.";
            type uint64;
          }
          leaf UnknownProtoPacketsReceived {
            config false;
            description
            "The total number of packets received via the
            interface which were discarded because of an
            unknown or unsupported  protocol.";
            type uint32;
          }
        }
        container QoS {
          description
          "The QoS object provides information on MoCA
          parameterized QoS for this interface
          {{bibref|MoCAv1.1}}.";
          leaf EgressNumFlows {
            config false;
            description
            "This parameter is based on
            ''mocaIfEgressNodeNumFlows'' from
            {{bibref|MOCA11-MIB}}.";
            type uint32;
          }
          leaf IngressNumFlows {
            config false;
            description
            "This parameter is based on
            ''mocaIfIngressNodeNumFlows'' from
            {{bibref|MOCA11-MIB}}.";
            type uint32;
          }
          leaf FlowStatsNumberOfEntries {
            config false;
            description
            "{{numentries}}";
            type uint32;
          }
          list FlowStats {
            key "FlowID";
            config false;
            description
            "The flow statistics table provides information on
            the MoCA parameterized QoS flows this interface has
            allocated onto the MoCA network.";
            leaf FlowID {
              config false;
              description
              "This parameter is based on ''mocaIfFlowID'' from
              {{bibref|MOCA11-MIB}}.";
              type uint32;
            }
            leaf PacketDA {
              config false;
              description
              "This parameter is based on ''mocaIfPacketDA''
              from {{bibref|MOCA11-MIB}}.";
              type yang:mac-address;
            }
            leaf MaxRate {
              config false;
              description
              "This parameter is based on ''mocaIfPeakDataRate''
              from {{bibref|MOCA11-MIB}}.";
              type uint32;
            }
            leaf MaxBurstSize {
              config false;
              description
              "This parameter is based on ''mocaIfBurstSize''
              from {{bibref|MOCA11-MIB}}.";
              type uint32;
            }
            leaf LeaseTime {
              config false;
              description
              "This parameter is based on ''mocaIfLeaseTime''
              from {{bibref|MOCA11-MIB}}.";
              type uint32;
            }
            leaf LeaseTimeLeft {
              config false;
              description
              "This parameter is based on
              ''mocaIfLeaseTimeLeft'' from
              {{bibref|MOCA11-MIB}}.";
              type uint32;
            }
            leaf FlowPackets {
              config false;
              description
              "This parameter is based on
              ''mocaIfTxPacketsFlow'' from
              {{bibref|MOCA11-MIB}}.";
              type uint32;
            }
          }
        }
        list AssociatedDevice {
          key "MACAddress";
          config false;
          description
          "This table contains information about other MoCA
          devices currently associated with this MoCA
          interface.";
          leaf MACAddress {
            config false;
            description
            "The MAC address of the associated device's MoCA
            interface.";
            type yang:mac-address;
          }
          leaf NodeID {
            config false;
            description
            "This parameter is based on ''mocaNodeIndex'' from
            {{bibref|MOCA11-MIB}}.";
            type uint32;
          }
          leaf PreferredNC {
            config false;
            description
            "This parameter is based on ''mocaNodePreferredNC''
            from {{bibref|MOCA11-MIB}}.";
            type boolean;
          }
          leaf HighestVersion {
            config false;
            description
            "This parameter is based on ''mocaNodeMocaVersion''
            from {{bibref|MOCA11-MIB}}.";
            type string {
              length "0..64";
              pattern "\\d+(\\.\\d+)*";
            }
          }
          leaf PHYTxRate {
            config false;
            description
            "This parameter is based on ''mocaMeshTxRate'' from
            {{bibref|MOCA11-MIB}}.";
            type uint32;
          }
          leaf PHYRxRate {
            config false;
            description
            "The PHY receive rate (in {{units}}) from this
            remote device.";
            type uint32;
          }
          leaf TxPowerControlReduction {
            config false;
            description
            "This parameter is based on
            ''mocaNodeTxPowerReduction'' from
            {{bibref|MOCA11-MIB}}.";
            type uint32;
          }
          leaf RxPowerLevel {
            config false;
            description
            "This parameter is based on ''mocaNodeRxPower'' from
            {{bibref|MOCA11-MIB}}.";
            type uint32;
          }
          leaf TxBcastRate {
            config false;
            description
            "This parameter is based on ''mocaNodeTxGcdRate''
            from {{bibref|MOCA11-MIB}}.";
            type uint32;
          }
          leaf RxBcastPowerLevel {
            config false;
            description
            "This parameter is based on ''mocaNodeRxGcdPower''
            from {{bibref|MOCA11-MIB}}.";
            type uint32;
          }
          leaf TxPackets {
            config false;
            description
            "The number of packets transmitted to this remote
            device (Note: Includes Broadcast, Multicast and
            Unicast packets).";
            type uint32;
          }
          leaf RxPackets {
            config false;
            description
            "This parameter is based on ''mocaNodeRxPackets''
            from {{bibref|MOCA11-MIB}}.";
            type uint32;
          }
          leaf RxErroredAndMissedPackets {
            config false;
            description
            "This parameter is based on ''mocaNodeRxDrops'' from
            {{bibref|MOCA11-MIB}}.";
            type uint32;
          }
          leaf QAM256Capable {
            config false;
            description
            "This parameter is based on
            ''mocaNodeQAM256Capable'' from
            {{bibref|MOCA11-MIB}}.";
            type boolean;
          }
          leaf PacketAggregationCapability {
            config false;
            description
            "This parameter is based on
            ''mocaNodePacketsAggrCapability'' from
            {{bibref|MOCA11-MIB}}.";
            type uint32 {
              range "0..10";
            }
          }
          leaf RxSNR {
            config false;
            description
            "This parameter is based on ''mocaNodeSNR'' from
            {{bibref|MOCA11-MIB}}.";
            type uint32;
          }
          leaf Active {
            config false;
            description
            "The ability to list inactive nodes is OPTIONAL.  If
            the CPE includes inactive nodes in this table,
            {{param}} MUST be set to {{false}}  for each
            inactive node.  The length of time an inactive node
            remains listed in this table is a local matter to
            the CPE.";
            type boolean;
          }
        }
      }
    }
    container Ghn {
      description
      "G.hn object that contains an {{object|Interface}} table
      for G.hn supported CPE. The ITU-T G.hn specifications
      {{bibref|G.9960}} and {{bibref|G.9961}} define Physical
      and MAC Layers for communication between two or more G.hn
      nodes in the home network over multiple wired media such
      as power line, phone line and coaxial cable.";
      leaf InterfaceNumberOfEntries {
        config false;
        description
        "{{numentries}}";
        type uint32;
      }
      list Interface {
        key "Name";
        unique "Alias";
        config true;
        description
        "G.hn interface table (a stackable interface object as
        described in {{bibref|TR-181i2|Section 4.2}}). Each
        table entry models the PHY {{bibref|G.9960}} and MAC
        {{bibref|G.9961}} layers of a G.hn interface.";
        leaf Enable {
          config true;
          description
          "This parameter is based on ''ifAdminStatus'' from
          {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config true;
          description
          "The textual name of the interface as assigned by the
          CPE.";
          type string {
            length "0..64";
          }
        }
        leaf LastChange {
          config false;
          description
          "The accumulated time in {{units}} since the interface
          entered its current operational state.";
          type uint32;
        }
        leaf-list LowerLayers {
          config true;
          description
          "Note: Since {{object}} is a layer 1 interface, it is
          expected that {{param}} will not be used.";
          type string;
        }
        leaf Upstream {
          config false;
          description
          "* For an End Device, {{param}} will be {{true}} for
          all interfaces.";
          type boolean;
        }
        leaf MACAddress {
          config false;
          description
          "Note: This is not necessarily the same as the
          Ethernet header source or destination MAC address,
          which is associated with the IP interface and is
          modeled via the
          {{param|.Ethernet.Link.{i}.MACAddress}} parameter.";
          type yang:mac-address;
        }
        leaf FirmwareVersion {
          config false;
          description
          "The firmware version of the interface.";
          type string {
            length "0..64";
          }
        }
        leaf ConnectionType {
          config false;
          description
          "This parameter is DEPRECATED because it has been
          replaced by {{param|MediumType}}.";
          type enumeration {
            enum "Powerline";
            enum "Phone";
            enum "Coax";
          }
        }
        leaf MaxTransmitRate {
          config false;
          description
          "The maximum PHY data rate that the interface is
          capable of transmitting (expressed in {{units}}).";
          type uint32;
        }
        leaf-list TargetDomainNames {
          config true;
          description
          "{{list}}  Identifies the target domains configured by
          the user, as described in {{bibref|G.9961|Section
          8.6.1}}. When registering or re-registering, the G.hn
          interface SHOULD try to register to one of these
          domains in the given order.";
          type string {
            length "0..32";
          }
        }
        leaf DomainName {
          config false;
          description
          "{{empty}} indicates that the interface is currently
          not registered.";
          type string {
            length "0..32";
          }
        }
        leaf DomainNameIdentifier {
          config false;
          description
          "The Domain Name Identifier, a shortened version of
          {{param|DomainName}}, denoted as DNI in
          {{bibref|G.9961|Section 8.6.11.2.1}}.";
          type uint32;
        }
        leaf DomainId {
          config false;
          description
          "The Domain Identifier of the domain to which the
          interface is registered, denoted as DOD in
          {{bibref|G.9961}}.";
          type uint32;
        }
        leaf DeviceId {
          config false;
          description
          "The value 0 indicates that the device is not
          currently registered.";
          type uint32;
        }
        leaf MaxBitRate {
          config false;
          description
          "The maximum PHY bit rate supported by this interface
          (expressed in {{units}}).";
          type uint32;
        }
        leaf NodeTypeDMCapable {
          config false;
          description
          "Indicates whether this interface has the capability
          to act as Domain Master in the G.hn domain.";
          type boolean;
        }
        leaf DMRequested {
          config true;
          description
          "Indicates a request to force the role of the G.hn
          interface to Domain Master (DM) for the G.hn domain
          it is connected to.  The selection of the Domain
          Master follows the procedures described in
          {{bibref|G.9961|Clause 8.6.6}}.";
          type boolean;
        }
        leaf IsDM {
          config false;
          description
          "Indicates whether this G.hn interface is currently
          the Domain Master (DM) for the G.hn domain it is
          connected to, as described in {{bibref|G.9961|Clause
          8.6}}.";
          type boolean;
        }
        leaf NodeTypeSCCapable {
          config false;
          description
          "Indicates whether this interface has the capability
          to act as Security Controller in the G.hn domain.";
          type boolean;
        }
        leaf SCRequested {
          config true;
          description
          "Indicates a request to force the role of the G.hn
          interface to Security Controller (SC) for the G.hn
          domain it is connected to.  The selection of the
          Security Controller follows the procedures described
          in {{bibref|G.9961|Clause 9.2}}.";
          type boolean;
        }
        leaf IsSC {
          config false;
          description
          "Indicates whether this G.hn interface is currently
          the Security Controller (SC) for the G.hn domain it
          is connected to, as described in
          {{bibref|G.9961|Clause 9.2}}.";
          type boolean;
        }
        leaf-list StandardVersions {
          config false;
          description
          "For example, to indicate support for the G.9960 base
          document and G.9961 amendment 1, the corresponding
          list would be \"G9960,0,G9961,1\".";
          type string;
        }
        leaf MaxBandPlan {
          config false;
          description
          "The largest bandplan that the interface can support,
          as defined in {{bibref|G.9961|Clause 8.8.5.5}}.";
          type uint32;
        }
        leaf MediumType {
          config false;
          description
          "The medium type that the interface currently operates
          on.  Refer to {{bibref|G.9962|Table 7-5}}.";
          type enumeration {
            enum "PowerLineBaseband";
            enum "PhoneLineBaseband";
            enum "CoaxBaseband";
            enum "CoaxRF";
            enum "PlasticOpticalFiber";
          }
        }
        leaf TAIFG {
          config false;
          description
          "The Acknowledgement InterFrame Gap, or TAIFG, as
          defined in {{bibref|G.9961|Clause 8.4}}. It is
          represented as multiples of {{units}}.";
          type uint32;
        }
        leaf NotchedAmateurRadioBands {
          config true;
          description
          "International Radio amateur bands are described in
          {{bibref|G.9964|Table D-1}} and conveyed by the
          Domain Master in the Amateur radio band descriptor
          (see {{bibref|G.9961|Table 8-77}}).";
          type yang:hex-string {
            length "0..2";
          }
        }
        leaf PHYThroughputDiagnosticsEnable {
          config true;
          description
          "Comma-separated list of DeviceIDs of nodes that need
          to enable their PHY throughput diagnostics mode.  All
          devices that are enabled will participate in the G.hn
          network PHY throughput diagnostics process.";
          type string;
        }
        leaf PerformanceMonitoringDiagnosticsEnable {
          config true;
          description
          "Comma-separated list of DeviceIDs of nodes that need
          to enable their Performance Monitoring diagnostics
          mode on this node.  All devices that are enabled will
          participate in the G.hn network Performance
          Monitoring diagnostics process.";
          type string;
        }
        leaf SMMaskedBandNumberOfEntries {
          config false;
          description
          "{{numentries}}";
          type uint32;
        }
        leaf NodeTypeDMConfig {
          config true;
          description
          "Note that, if more than one node is configured to act
          as Domain Master, G.hn specifies a protocol to ensure
          only one device actually becomes DM.";
          type boolean;
        }
        leaf NodeTypeDMStatus {
          config false;
          description
          "See Note in {{param|NodeTypeDMConfig}} regarding the
          possibility of more than one node being configured
          with {{param|NodeTypeDMConfig}} = {{true}}.";
          type boolean;
        }
        leaf NodeTypeSCStatus {
          config false;
          description
          "Indicates whether the interface is acting as Security
          Controller ({{true}}) or not ({{false}}).";
          type boolean;
        }
        leaf AssociatedDeviceNumberOfEntries {
          config false;
          description
          "{{numentries}}";
          type uint32;
        }
        leaf-list PSM {
          config true;
          description
          "For example, a PSM defined by two breakpoints
          (subcarrier 450, PSM level -80 dBm/Hz) and
          (subcarrier 1050, PSM level -90 dBm/Hz) is
          represented by PSM [450,600],[1050,500] .";
          type PSMBreakPointIndexAndLevel;
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "Note: LPDUs in mixed LLC frame blocks are
            considered data LPDUs.";
            type yang:counter32;
          }
          leaf BytesReceived {
            config false;
            description
            "Note: LPDUs in mixed LLC frame blocks are
            considered data LPDUs.";
            type yang:counter32;
          }
          leaf PacketsSent {
            config false;
            description
            "More specifically, this is the total number of
            APDUs requested for transmission by a higher layer
            (i.e., outbound APDUs at the x1 reference point
            defined in {{bibref|G.9960|Clause 5.2.1}}) that
            were transmitted by the node through the physical
            medium.  It does not include transmitted LCDUs.";
            type yang:counter32;
          }
          leaf PacketsReceived {
            config false;
            description
            "More specifically, this is the total number of
            APDUs delivered to a higher layer (i.e., inbound
            APDUs at the x1 reference point) that were received
            by the node through the physical medium.  It does
            not include received LCDUs.";
            type yang:counter32;
          }
          leaf ErrorsSent {
            config false;
            description
            "More specifically, this is the total number of
            APDUs that were requested for transmission by a
            higher layer (i.e., outbound APDUs at the x1
            reference point defined in {{bibref|G.9960|Clause
            5.2.1}}) but could not be transmitted because of
            errors (e.g., APDUs containing CRC errors).";
            type yang:counter32;
          }
          leaf ErrorsReceived {
            config false;
            description
            "More specifically, this is the total number of
            received APDUs that contained errors preventing
            them from being delivered to a higher layer (i.e.,
            inbound APDUs at the x1 reference point defined in
            {{bibref|G.9960|Clause 5.2.1}}). The possible
            causes of error are: incorrect CRC, incorrect MIC,
            incorrect MIC size, and incorrect size of packet.";
            type yang:counter32;
          }
          leaf UnicastPacketsSent {
            config false;
            description
            "More specifically, this is the total number of
            APDUs that were requested for transmission by a
            higher layer (i.e., outbound APDUs at the x1
            reference point) and which were addressed to a
            unicast address at this layer.  It includes APDUs
            that were discarded or not sent.";
            type yang:counter32;
          }
          leaf UnicastPacketsReceived {
            config false;
            description
            "More specifically, this is the total number of
            received APDUs that were delivered to a higher
            layer (i.e., inbound APDUs at the x1 reference
            point) and which were addressed to a unicast
            address at this layer.";
            type yang:counter32;
          }
          leaf DiscardPacketsSent {
            config false;
            description
            "More specifically, this is the total number of
            APDUs that were requested for transmission by a
            higher layer (i.e., outbound APDUs at the x1
            reference point) but chosen to be discarded even
            though no errors had been detected to prevent their
            being transmitted (e.g., buffer overflow).";
            type yang:counter32;
          }
          leaf DiscardPacketsReceived {
            config false;
            description
            "More specifically, this is the total number of
            received APDUs that were chosen to be discarded
            even though no errors had been detected to prevent
            their being delivered.";
            type yang:counter32;
          }
          leaf MulticastPacketsSent {
            config false;
            description
            "More specifically, this is the total number of
            APDUs that were requested for transmission by a
            higher layer (i.e., outbound APDUs at the x1
            reference point) and which were addressed to a
            multicast address at this layer.  It includes APDUs
            that were discarded or not sent.";
            type yang:counter32;
          }
          leaf MulticastPacketsReceived {
            config false;
            description
            "More specifically, this is the total number of
            received APDUs that were delivered to a higher
            layer (i.e., inbound APDUs at the x1 reference
            point) and which were addressed to a multicast
            address at this layer.";
            type yang:counter32;
          }
          leaf BroadcastPacketsSent {
            config false;
            description
            "More specifically, this is the total number of
            APDUs that were requested for transmission by a
            higher layer (i.e., outbound APDUs at the x1
            reference point) and which were addressed to a
            broadcast address at this layer.  It includes APDUs
            that were discarded or not sent.";
            type yang:counter32;
          }
          leaf BroadcastPacketsReceived {
            config false;
            description
            "More specifically, this is the total number of
            received APDUs that were delivered to a higher
            layer (i.e., inbound APDUs at the x1 reference
            point) and which were addressed to a broadcast
            address at this layer.";
            type yang:counter32;
          }
          leaf UnknownProtoPacketsReceived {
            config false;
            description
            "More specifically, this is the total number of
            APDUs received by the management that were
            discarded because of an unknown or unsupported
            protocol.";
            type yang:counter32;
          }
          leaf MgmtBytesSent {
            config false;
            description
            "The total number of MPDU bytes transmitted by the
            node through a physical medium, which correspond to
            management LPDUs and framing overhead.";
            type yang:counter32;
          }
          leaf MgmtBytesReceived {
            config false;
            description
            "The total number of MPDU bytes received by the node
            through a physical medium, which correspond to
            management LPDUs and framing overhead.";
            type yang:counter32;
          }
          leaf MgmtPacketsSent {
            config false;
            description
            "The total number of LCDUs requested for
            transmission by a management layer (i.e., outbound
            LCDUs generated in LLC defined in
            {{bibref|G.9961|Clause 8.1.3}}) that were
            transmitted by the node through a physical medium.";
            type yang:counter32;
          }
          leaf MgmtPacketsReceived {
            config false;
            description
            "The total number of LCDUs delivered to a management
            layer (i.e., inbound LCDUs) that were received by
            the node through a physical medium.";
            type yang:counter32;
          }
          leaf BlocksSent {
            config false;
            description
            "The total number of LPDUs that were transmitted by
            the node through a physical medium, regardless of
            new or retransmitted LPDUs.";
            type yang:counter32;
          }
          leaf BlocksReceived {
            config false;
            description
            "The total number of LPDUs that were received by the
            node through a physical medium, with or without
            errors.";
            type yang:counter32;
          }
          leaf BlocksResent {
            config false;
            description
            "The total number of LPDUs that were retransmitted.";
            type yang:counter32;
          }
          leaf BlocksErrorsReceived {
            config false;
            description
            "* Block error rate = BlocksErrorReceived /
            BlocksReceived.";
            type yang:counter32;
          }
        }
        list AssociatedDevice {
          key "MACAddress";
          config false;
          description
          "This table contains information about other G.hn
          devices connected to this G.hn interface.";
          leaf MACAddress {
            config false;
            description
            "This is denoted as REGID in {{bibref|G.9961}}.";
            type yang:mac-address;
          }
          leaf DeviceId {
            config false;
            description
            "Device Id (as defined in G.hn) for the remote G.hn
            device, denoted as DEVICE_ID in {{bibref|G.9961}}.";
            type uint32;
          }
          leaf TxPhyRate {
            config false;
            description
            "Refer to Note 1 of {{bibref|G.9961|Table 8-48}}.
            To convert from the value in the table, divide by
            32K (32768) and round down.";
            type uint32;
          }
          leaf RxPhyRate {
            config false;
            description
            "Refer to Note 1 of {{bibref|G.9961|Table 8-48}}.
            To convert from the value in the table, divide by
            32K (32768) and round down.";
            type uint32;
          }
          leaf Active {
            config false;
            description
            "If {{param}} is {{true}}, it indicates that the
            Status of the remote device is 0, 1, or 2 (see
            {{bibref|G.9961|Table 7-3}}).";
            type boolean;
          }
        }
        container DMInfo {
          description
          "This object specifies management parameters
          pertaining to the domain functionality (Domain Master
          function; see {{bibref|G.9961|Clause 8.6}}). The
          object exists only on G.hn interfaces that are
          currently the Domain Master, i.e.  for which
          parameter {{param|#.IsDM}} is {{true}}.";
          leaf DomainName {
            config true;
            description
            "This is the domain name to which the interface is
            currently registered.  {{empty}} indicates that the
            interface is currently not registered.";
            type yang:hex-string {
              length "0..32";
            }
          }
          leaf DomainNameIdentifier {
            config false;
            description
            "The Domain Name Identifier, a shortened version of
            {{param|DomainName}}, denoted as DNI in
            {{bibref|G.9961|Section 8.6.11.2.1}}.";
            type yang:hex-string {
              length "0..2";
            }
          }
          leaf DomainId {
            config false;
            description
            "The Domain Identifier of the domain to which the
            interface is registered, denoted as DOD in
            {{bibref|G.9961}}.";
            type uint32;
          }
          leaf MACCycleDuration {
            config true;
            description
            "The MAC cycle duration, as specified in
            {{bibref|G.9961|Clause 8.4}}. It is represented as
            multiples of {{units}}. In the case of power line,
            writing to this parameter has no effect and it
            reads back as 0, which is a special value
            indicating that the MAC cycle is synchronized with
            2 AC cycles as defined in {{bibref|G.9961|Clause
            8.6.3.1}}.";
            type uint32 {
              range "0|10..200";
            }
          }
          leaf SCDeviceId {
            config true;
            description
            "The DEVICE_ID of the Security Controller selected
            by the Domain Master.";
            type uint32;
          }
          leaf SCMACAddress {
            config true;
            description
            "The REGID of the Security Controller selected by
            the Domain Master.";
            type yang:mac-address;
          }
          leaf ReregistrationTimePeriod {
            config true;
            description
            "The time interval for periodic re-registration, as
            specified in {{bibref|G.9961|Clause 8.8.5.8}}. It
            is represented as multiples of {{units}}.";
            type uint32 {
              range "5..63";
            }
          }
          leaf TopologyPeriodicInterval {
            config true;
            description
            "The time interval that a node sends out the
            periodic topology update using
            TM_NodeTopologyChange.ind message, as specified in
            {{bibref|G.9961|Clause 8.8.5.8.1}}. It is
            represented as multiples of {{units}}. The special
            value 0 represents an infinite interval (i.e., no
            periodic topology update).";
            type uint32 {
              range "0..255";
            }
          }
          leaf MinSupportedBandplan {
            config true;
            description
            "Indicates the value of the minimal bandplan
            capability for a node that is allowed to register
            to the domain.";
            type uint32;
          }
          leaf MaxSupportedBandplan {
            config true;
            description
            "Indicates the value of the minimal bandplan
            capability for a node that is allowed to register
            to the domain.";
            type uint32;
          }
        }
        container SCInfo {
          description
          "This object specifies management parameters
          pertaining to the Security Controller functionality
          (Security Controller function; see
          {{bibref|G.9961|Clause 9.2}}). The object exists only
          on G.hn interfaces that are currently the Security
          Controller, i.e.  for which parameter
          {{param|#.IsSC}} is {{true}}.";
          leaf-list ModesSupported {
            config false;
            description
            "The security modes that the Security Controller can
            support.  Refer to {{bibref|G.9961|Clause 9.2}}.";
            type enumeration {
              enum "NN" {
                description
                "Node-to-Node";
              }
              enum "NMK" {
                description
                "Network Membership Key";
              }
            }
          }
          leaf ModeEnabled {
            config true;
            description
            "The security mode in which the Security Controller
            is operating.";
            type string;
            must ". = ../ModesSupported";
          }
          leaf MICSize {
            config true;
            description
            "The selected MIC size used in the domain.";
            type enumeration {
              enum "4-byte MIC";
              enum "8-byte MIC";
              enum "16-byte MIC";
            }
          }
          leaf Location {
            config false;
            description
            "Indicates whether the Security Controller is above
            the L1 reference point.  It is set to {{true}} if
            the Security Controller is above the L1 reference
            point, and set to {{false}} otherwise.";
            type boolean;
          }
        }
        list SMMaskedBand {
          key "BandNumber";
          config true;
          description
          "Instances of this object are expected to exist only
          on G.hn interfaces that are currently the Domain
          Master, i.e.  for which parameter {{param|#.IsDM}} is
          {{true}}.";
          leaf Enable {
            config true;
            description
            "Enables or disables the {{object}}.";
            type boolean;
          }
          leaf BandNumber {
            config true;
            description
            "The masked band number.";
            type uint32;
          }
          leaf StartSubCarrier {
            config true;
            description
            "Index of the lowest frequency sub-carrier in the
            band to be masked as specified in
            {{bibref|G.9961|Table 8-79}}. This parameter is
            writable only on the interface which acts as the
            Domain Master.";
            type uint32;
          }
          leaf StopSubCarrier {
            config true;
            description
            "Index of the highest frequency sub-carrier in the
            band to be masked as specified in Table 8-79 in
            {{bibref|G.9961}}. This parameter is writable only
            on the interface which acts as the Domain Master.";
            type uint32;
          }
        }
      }
      container Diagnostics {
        description
        "The G.hn Diagnostics object.";
        container PHYThroughput {
          description
          "When diagnostics are requested, all G.hn nodes for
          which the
          {{param|##.Interface.{i}.PHYThroughputDiagnosticsEnable}}
          parameter is set enter PHY diagnostics mode.";
          leaf DiagnosticsState {
            config true;
            description
            "{{datatype|expand}}";
            type DiagnosticsState;
          }
          leaf Interface {
            config true;
            description
            "The interface over which the test is to be
            performed.";
            type string;
          }
          leaf DiagnoseMACAddress {
            config true;
            description
            "Note: This MAC address might belong to another node
            of the domain.";
            type yang:mac-address;
          }
          leaf PHYThroughputResultNumberOfEntries {
            config false;
            description
            "{{numentries}}";
            type uint32;
          }
          list Result {
            key "DestinationMACAddress";
            config false;
            description
            "PHY throughput diagnostics results.";
            leaf DestinationMACAddress {
              config false;
              description
              "MAC address of the destination node of the link
              being measured.";
              type yang:mac-address;
            }
            leaf LinkState {
              config false;
              description
              "Indicates the state of the link between the G.hn
              Interface with MAC address
              {{param|#.DiagnoseMACAddress}} and the G.hn
              Interface with MAC address
              {{param|DestinationMACAddress}}.";
              type enumeration {
                enum "Direct" {
                  description
                  "There is a direct link between G.hn Interface
                  with MAC address
                  {{param|#.DiagnoseMACAddress}} and G.hn
                  Interface with MAC address
                  {{param|DestinationMACAddress}}";
                }
                enum "NonDirect" {
                  description
                  "There is no direct link between G.hn
                  Interface with MAC address
                  {{param|#.DiagnoseMACAddress}} and G.hn
                  Interface with MAC address
                  {{param|DestinationMACAddress}}";
                }
              }
            }
            leaf TxPhyRate {
              config false;
              description
              "PHY data rate in transmit direction in the link
              between the G.hn Interface with MAC address
              {{param|#.DiagnoseMACAddress}} and the G.hn
              Interface with MAC address
              {{param|DestinationMACAddress}}. It is
              represented in {{units}} as defined in Note 1 to
              {{bibref|G.9961|Table 8-48}}.  To convert from
              the value in the table, divide by 32K (32768) and
              round down.";
              type uint32;
            }
            leaf RxPhyRate {
              config false;
              description
              "PHY data rate in receive direction in the link
              between the G.hn Interface with MAC address
              {{param|#.DiagnoseMACAddress}}  and the G.hn
              Interface with MAC address
              {{param|DestinationMACAddress}}. It is
              represented in {{units}} as defined in Note 1 to
              {{bibref|G.9961|Table 8-48}}.  To convert from
              the value in the table, divide by 32K (32768) and
              round down.";
              type uint32;
            }
          }
        }
        container PerformanceMonitoring {
          description
          "When diagnostics are requested, all G.hn nodes for
          which the
          {{param|##.Interface.{i}.PerformanceMonitoringDiagnosticsEnable}}
          parameter is set enter PHY diagnostics mode.";
          leaf DiagnosticsState {
            config true;
            description
            "{{datatype|expand}}";
            type DiagnosticsState;
          }
          leaf Interface {
            config true;
            description
            "The interface over which the test is to be
            performed.";
            type string;
          }
          leaf DiagnoseMACAddress {
            config true;
            description
            "Note: This MAC address might belong to another node
            of the domain.";
            type yang:mac-address;
          }
          leaf SampleInterval {
            config true;
            description
            "If SampleInterval is a simple fraction of a day,
            e.g.  900 (a quarter of an hour) or 3600 (an hour),
            the device MAY choose to align sample intervals
            with time of day, but is not required to do so.";
            type uint32;
          }
          leaf SNRGroupLength {
            config true;
            description
            "The number of sub-carriers in a group to be used
            for averaging SNR values when providing SNR
            information for a channel.";
            type uint32 {
              range "1|2|4|8|16|32|64|128|256";
            }
          }
          container Nodes {
            description
            "Note: Packets in statistics counters are Ethernet
            packets.";
            leaf CurrentStart {
              config false;
              description
              "When automatic collection is disabled, i.e.
              SampleInterval is zero, the current interval
              started two manual samples ago.";
              type yang:date-and-time;
            }
            leaf CurrentEnd {
              config false;
              description
              "When automatic collection is disabled, i.e.
              SampleInterval is zero, the current interval
              ended at the most recent manual sample.";
              type yang:date-and-time;
            }
            leaf NodeNumberOfEntries {
              config false;
              description
              "{{numentries}} This is the number of G.hn nodes
              for which performance monitoring results were
              collected during the current sample interval.";
              type uint32;
            }
            list Node {
              key "DestinationMACAddress";
              config false;
              description
              "Note: Packet counters indicate the number of
              packets received between {{param|#.CurrentStart}}
              and {{param|#.CurrentEnd}}.";
              leaf DestinationMACAddress {
                config false;
                description
                "MAC address of the destination node of the link
                being measured.";
                type yang:mac-address;
              }
              leaf BytesSent {
                config false;
                description
                "Note: LPDUs in mixed LLC frame blocks are
                considered data LPDUs.";
                type yang:counter32;
              }
              leaf BytesReceived {
                config false;
                description
                "Note: LPDUs in mixed LLC frame blocks are
                considered data LPDUs.";
                type yang:counter32;
              }
              leaf PacketsSent {
                config false;
                description
                "The total number of APDUs requested for
                transmission by a higher layer (i.e., outbound
                APDUs at the x1 reference point defined in
                {{bibref|G.9960|Clause 5.2.1}}) that were
                transmitted by the node through the physical
                medium.  It does not include transmitted LCDUs.";
                type yang:counter32;
              }
              leaf PacketsReceived {
                config false;
                description
                "The total number of APDUs delivered to a higher
                layer (i.e., inbound APDUs at the x1 reference
                point) that were received by the node through
                the physical medium.  It does not include
                received LCDUs.";
                type yang:counter32;
              }
              leaf ErrorsSent {
                config false;
                description
                "The total number of APDUs that were requested
                for transmission by a higher layer (i.e.,
                outbound APDUs at the x1 reference point
                defined in {{bibref|G.9960|Clause 5.2.1}}).
                This parameter represents the total number of
                LCDUs requested for transmission by a
                management layer (i.e., outbound LCDUs
                generated in LLC defined in in
                {{bibref|G.9961|Clause 8.1.3}}) that were
                transmitted by the node through a physical
                medium) but could not be transmitted because of
                errors (e.g., APDUs containing CRC errors).";
                type yang:counter32;
              }
              leaf ErrorsReceived {
                config false;
                description
                "The total number of received APDUs that
                contained errors preventing them from being
                delivered to a higher layer (i.e., inbound
                APDUs at the x1 reference point defined in
                {{bibref|G.9960|Clause 5.2.1}}). The possible
                causes of error are: incorrect CRC, incorrect
                MIC, incorrect MIC size, and incorrect size of
                packet.";
                type yang:counter32;
              }
              leaf UnicastPacketsSent {
                config false;
                description
                "The total number of APDUs that were requested
                for transmission by a higher layer (i.e.,
                outbound APDUs at the x1 reference point) and
                which were addressed to a unicast address at
                this layer.  It includes APDUs that were
                discarded or not sent.";
                type yang:counter32;
              }
              leaf UnicastPacketsReceived {
                config false;
                description
                "The total number of received APDUs that were
                delivered to a higher layer (i.e., inbound
                APDUs at the x1 reference point) and which were
                addressed to a unicast address at this layer.";
                type yang:counter32;
              }
              leaf DiscardPacketsSent {
                config false;
                description
                "The total number of APDUs that were requested
                for transmission by a higher layer (i.e.,
                outbound APDUs at the x1 reference point) but
                chosen to be discarded even though no errors
                had been detected to prevent their being
                transmitted (e.g., buffer overflow).";
                type yang:counter32;
              }
              leaf DiscardPacketsReceived {
                config false;
                description
                "The total number of received APDUs that were
                chosen to be discarded even though no errors
                had been detected to prevent their being
                delivered.";
                type yang:counter32;
              }
              leaf MulticastPacketsSent {
                config false;
                description
                "The total number of APDUs that were requested
                for transmission by a higher layer (i.e.,
                outbound APDUs at the x1 reference point) and
                which were addressed to a multicast address at
                this layer.  It includes APDUs that were
                discarded or not sent.";
                type yang:counter32;
              }
              leaf MulticastPacketsReceived {
                config false;
                description
                "The total number of received APDUs that were
                delivered to a higher layer (i.e., inbound
                APDUs at the x1 reference point) and which were
                addressed to a multicast address at this layer.";
                type yang:counter32;
              }
              leaf BroadcastPacketsSent {
                config false;
                description
                "The total number of APDUs that were requested
                for transmission by a higher layer (i.e.,
                outbound APDUs at the x1 reference point) and
                which were addressed to a broadcast address at
                this layer.  It includes APDUs that were
                discarded or not sent.";
                type yang:counter32;
              }
              leaf BroadcastPacketsReceived {
                config false;
                description
                "The total number of received APDUs that were
                delivered to a higher layer (i.e., inbound
                APDUs at the x1 reference point) and which were
                addressed to a broadcast address at this layer.";
                type yang:counter32;
              }
              leaf UnknownProtoPacketsReceived {
                config false;
                description
                "The total number of APDUs received by the
                management that were discarded because of an
                unknown or unsupported protocol.";
                type yang:counter32;
              }
              leaf MgmtBytesSent {
                config false;
                description
                "The total number of MPDU bytes transmitted by
                the node through a physical medium, which
                correspond to management LPDUs and framing
                overhead.";
                type yang:counter32;
              }
              leaf MgmtBytesReceived {
                config false;
                description
                "The total number of MPDU bytes received by the
                node through a physical medium, which
                correspond to management LPDUs and framing
                overhead.";
                type yang:counter32;
              }
              leaf MgmtPacketsSent {
                config false;
                description
                "The total number of LCDUs requested for
                transmission by a management layer (i.e.,
                outbound LCDUs generated in LLC defined in
                {{bibref|G.9961|Clause 8.1.3}}) that were
                transmitted by the node through a physical
                medium.";
                type yang:counter32;
              }
              leaf MgmtPacketsReceived {
                config false;
                description
                "The total number of LCDUs delivered to a
                management layer (i.e., inbound LCDUs) that
                were received by the node through a physical
                medium.";
                type yang:counter32;
              }
              leaf BlocksSent {
                config false;
                description
                "The total number of LPDUs that were transmitted
                by the node through a physical medium,
                regardless of new or retransmitted LPDUs.";
                type yang:counter32;
              }
              leaf BlocksReceived {
                config false;
                description
                "The total number of LPDUs that were received by
                the node through a physical medium, with or
                without errors.";
                type yang:counter32;
              }
              leaf BlocksResent {
                config false;
                description
                "The total number of LPDUs that were
                retransmitted.";
                type yang:counter32;
              }
              leaf BlocksErrorsReceived {
                config false;
                description
                "* Block error rate = BlocksErrorReceived /
                BlocksReceived.";
                type yang:counter32;
              }
            }
          }
          container Channels {
            description
            "Note: channels are unidirectional.";
            leaf TimeStamp {
              config false;
              description
              "Time at which channel data was last collected.";
              type yang:date-and-time;
            }
            leaf ChannelNumberOfEntries {
              config false;
              description
              "{{numentries}}";
              type uint32;
            }
            list Channel {
              key "DestinationMACAddress";
              config false;
              description
              "Per-channel G.hn performance monitoring results
              during the current sample interval.  Each table
              entry contains the results collected from the
              channel between a G.hn interface (as indicated by
              {{param|##.DiagnoseMACAddress}}) and a G.hn
              interface indicated by
              {{param|DestinationMACAddress}})";
              leaf DestinationMACAddress {
                config false;
                description
                "MAC address of the destination node of the link
                being measured.";
                type yang:mac-address;
              }
              leaf-list SNR {
                config false;
                description
                "The result of an SNR test performed over the
                channel.  It is formatted as a comma-separated
                list of N/M unsigned integers that represents
                the result of Signal-to-Noise-Ratio measurement
                averaging in groups of M subcarriers.  The
                number N depends on the bandplan used by the
                node and corresponds to the OFDM control
                parameter N of each medium as defined in
                {{bibref|G.9964}}. The number M corresponds to
                the parameter {{param|##.SNRGroupLength}}.";
                type uint32;
              }
            }
          }
        }
      }
    }
    container HomePlug {
      description
      "HomePlug object that contains the {{object|Interface}}
      table.  The HomePlug industry standard {{bibref|HPAV1.1}}
      defines peer to peer communication over powerline medium.";
      leaf InterfaceNumberOfEntries {
        config false;
        description
        "{{numentries}}";
        type uint32;
      }
      list Interface {
        key "Name";
        unique "Alias";
        config true;
        description
        "HomePlug interface table (a stackable interface object
        as described in {{bibref|TR-181i2|Section 4.2}}). Each
        table entry models the PHY and MAC levels of a HomePlug
        interface {{bibref|HPAV1.1}}.";
        leaf Enable {
          config true;
          description
          "This parameter is based on ''ifAdminStatus'' from
          {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config true;
          description
          "The textual name of the interface as assigned by the
          CPE.";
          type string {
            length "0..64";
          }
        }
        leaf LastChange {
          config false;
          description
          "The accumulated time in {{units}} since the interface
          entered its current operational state.";
          type uint32;
        }
        leaf-list LowerLayers {
          config true;
          description
          "Note: Since {{object}} is a layer 1 interface, it is
          expected that {{param}} will not be used.";
          type string;
        }
        leaf Upstream {
          config false;
          description
          "* For an End Device, {{param}} will be {{true}} for
          all interfaces.";
          type boolean;
        }
        leaf MACAddress {
          config false;
          description
          "Note: This is not necessarily the same as the
          Ethernet header source or destination MAC address,
          which is associated with the IP interface and is
          modeled via the
          {{param|.Ethernet.Link.{i}.MACAddress}} parameter.";
          type yang:mac-address;
        }
        leaf LogicalNetwork {
          config true;
          description
          "The textual name of the HomePlug Logical Network.";
          type string {
            length "0..64";
          }
        }
        leaf Version {
          config false;
          description
          ": \"1.1\"";
          type string {
            length "0..16";
          }
        }
        leaf FirmwareVersion {
          config false;
          description
          "The firmware version of the interface.";
          type string {
            length "0..64";
          }
        }
        leaf ForceCCo {
          config true;
          description
          "Typically {{param}} is set to automatic CCo selection
          ({{false}}).";
          type boolean;
          default "false";
        }
        leaf NetworkPassword {
          config true;
          description
          "The network password of the device.  This is a human
          readable ASCII string that is hashed per the HomePlug
          specification to generate the Network Membership Key
          (NMK). Note that care needs to be taken when setting
          this parameter as it might prohibit communication
          with other adapters or equipment connected via the
          powerline network.";
          type string {
            length "0..32";
          }
        }
        leaf-list OtherNetworksPresent {
          config false;
          description
          ": \"Other\"";
          type string;
        }
        leaf MaxBitRate {
          config false;
          description
          "The maximum PHY bit rate supported by this interface
          (expressed in {{units}}).";
          type uint32;
        }
        leaf AssociatedDeviceNumberOfEntries {
          config false;
          description
          "{{numentries}}";
          type uint32;
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "The total number of packets that higher-level
            protocols requested for transmission and which were
            addressed to a broadcast address at this layer,
            including those that were discarded or not sent.";
            type uint64;
          }
          leaf BroadcastPacketsReceived {
            config false;
            description
            "The total number of received packets, delivered by
            this layer to a higher layer, which were addressed
            to a broadcast address at this layer.";
            type uint64;
          }
          leaf UnknownProtoPacketsReceived {
            config false;
            description
            "The total number of packets received via the
            interface which were discarded because of an
            unknown or unsupported  protocol.";
            type uint32;
          }
          leaf MPDUTxAck {
            config false;
            description
            "HomePlug-specific statistic.  The Number of MAC
            Protocol Data Units (MPDUs) Transmitted and
            Acknowledged.";
            type uint64;
          }
          leaf MPDUTxCol {
            config false;
            description
            "HomePlug-specific statistic.  The Number of MAC
            Protocol Data Units (MPDUs) Transmitted and
            Collided";
            type uint64;
          }
          leaf MPDUTxFailed {
            config false;
            description
            "HomePlug-specific statistic.  The Number of MAC
            Protocol Data Units (MPDUs) Transmitted and Failed";
            type uint64;
          }
          leaf MPDURxAck {
            config false;
            description
            "HomePlug-specific statistic.  The Number of MAC
            Protocol Data Units (MPDUs) Received and
            Acknowledged";
            type uint64;
          }
          leaf MPDURxFailed {
            config false;
            description
            "HomePlug-specific statistic.  The Number of MAC
            Protocol Data Units (MPDUs) Received and Failed";
            type uint64;
          }
        }
        list AssociatedDevice {
          key "MACAddress";
          config false;
          description
          "This table contains information about other HomePlug
          devices connected to this HomePlug interface.";
          leaf MACAddress {
            config false;
            description
            "MAC address of remote HomePlug device.  It is used
            to uniquely identify and easily correlate with the
            connected remote HomePlug device.";
            type yang:mac-address;
          }
          leaf TxPhyRate {
            config false;
            description
            "The PHY transmit Rate (expressed in {{units}}) to
            this remote device.";
            type uint32;
          }
          leaf RxPhyRate {
            config false;
            description
            "The PHY receive Rate (expressed in {{units}}) from
            this remote device.";
            type uint32;
          }
          leaf-list SNRPerTone {
            config false;
            description
            "{{list}} List items indicate Signal to Noise Ratio
            (SNR) per tone from this remote device (expressed
            in {{units}}).";
            type uint32;
          }
          leaf AvgAttenuation {
            config false;
            description
            "Average attenuation from this remote device
            (expressed in {{units}}).";
            type uint32;
          }
          leaf-list EndStationMACs {
            config false;
            description
            "For example: \"11:22:33:AA:BB:CC,
            22:33:44:DD:EE:66\"";
            type yang:mac-address;
          }
          leaf Active {
            config false;
            description
            "The ability to list inactive nodes is OPTIONAL. If
            the CPE includes inactive nodes in this table,
            {{param}} MUST be set to {{false}} for each
            inactive node.  The length of time an inactive node
            remains listed in this table is a local matter to
            the CPE.";
            type boolean;
          }
        }
      }
    }
    container UPA {
      description
      "Universal Powerline Association {{bibref|UPA-PLC}}. This
      object contains the {{object|Interface}} and
      {{object|Diagnostics}} objects.";
      leaf InterfaceNumberOfEntries {
        config false;
        description
        "{{numentries}}";
        type uint32;
      }
      list Interface {
        key "Name";
        unique "Alias";
        config true;
        description
        "UPA interface table (a stackable interface object as
        described in {{bibref|TR-181i2|Section 4.2}}). Each
        table entry models the PHY and MAC levels of a UPA
        interface {{bibref|UPA-PLC}}.";
        leaf Enable {
          config true;
          description
          "This parameter is based on ''ifAdminStatus'' from
          {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config true;
          description
          "The textual name of the interface as assigned by the
          CPE.";
          type string {
            length "0..64";
          }
        }
        leaf LastChange {
          config false;
          description
          "The accumulated time in {{units}} since the interface
          entered its current operational state.";
          type uint32;
        }
        leaf-list LowerLayers {
          config true;
          description
          "Note: Since {{object}} is a layer 1 interface, it is
          expected that {{param}} will not be used.";
          type string;
        }
        leaf Upstream {
          config false;
          description
          "* For an End Device, {{param}} will be {{true}} for
          all interfaces.";
          type boolean;
        }
        leaf MACAddress {
          config false;
          description
          "Note: This is not necessarily the same as the
          Ethernet header source or destination MAC address,
          which is associated with the IP interface and is
          modeled via the
          {{param|.Ethernet.Link.{i}.MACAddress}} parameter.";
          type yang:mac-address;
        }
        leaf FirmwareVersion {
          config false;
          description
          "This interface's firmware version.";
          type string {
            length "0..64";
          }
        }
        leaf MaxBitRate {
          config false;
          description
          "The maximum PHY bit rate supported by this interface
          (expressed in {{units}}).";
          type uint32;
        }
        leaf NodeType {
          config true;
          description
          "Type of UPA device role.  It can be Fixed Access
          Point (master) or End Point (slave) of the PLC
          network.  {{enum}}";
          type enumeration {
            enum "AP";
            enum "EP";
          }
        }
        leaf LogicalNetwork {
          config true;
          description
          "The name (network ID) of the logical PLC network in
          which the local interface is a member (human readable
          string).";
          type string {
            length "0..20";
          }
        }
        leaf EncryptionMethod {
          config true;
          description
          "Encryption Method used by UPA device.  {{enum}}";
          type enumeration {
            enum "None";
            enum "DES";
            enum "3DES";
            enum "AES128";
            enum "AES256";
          }
        }
        leaf EncryptionKey {
          config true;
          description
          "This a human readable string used by the system to
          generate the encryption key to encrypt communications
          in powerline.  It takes non extended ASCII characters
          (i.e.  printable 7-bit ASCII character codes 32-126,
          which includes SPACE but excludes TAB, LF and CR).
          For example: bvjPekZiYUf9kjNKJASkgJ09adfoP01Fjvgd";
          type string {
            length "0..36";
          }
        }
        leaf PowerBackoffEnabled {
          config true;
          description
          "Power back-off management feature status in the UPA
          device.  Boolean can be {{true}} for \"enabled\" and
          {{false}}  for \"disabled\".";
          type boolean;
        }
        leaf PowerBackoffMechanismActive {
          config false;
          description
          "Show if power back-off mechanism is active at that
          time in the UPA device.  Boolean can be {{true}} for
          \"active\"  and {{false}} for \"not active\".";
          type boolean;
        }
        leaf EstApplicationThroughput {
          config false;
          description
          "The estimated application throughput (expressed in
          {{units}}), received from the PLC link.  This value
          can be  used to indicate link quality.";
          type uint32;
        }
        leaf ActiveNotchEnable {
          config true;
          description
          "Enables or disables the {{object|ActiveNotch}} table
          for this interface.";
          type boolean;
        }
        leaf ActiveNotchNumberOfEntries {
          config false;
          description
          "{{numentries}}";
          type uint32;
        }
        leaf AssociatedDeviceNumberOfEntries {
          config false;
          description
          "{{numentries}}";
          type uint32;
        }
        leaf BridgeForNumberOfEntries {
          config false;
          description
          "{{numentries}}";
          type uint32;
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "The total number of packets that higher-level
            protocols requested for transmission and which were
            addressed to a broadcast address at this layer,
            including those that were discarded or not sent.";
            type uint64;
          }
          leaf BroadcastPacketsReceived {
            config false;
            description
            "The total number of received packets, delivered by
            this layer to a higher layer, which were addressed
            to a broadcast address at this layer.";
            type uint64;
          }
          leaf UnknownProtoPacketsReceived {
            config false;
            description
            "The total number of packets received via the
            interface which were discarded because of an
            unknown or unsupported  protocol.";
            type uint32;
          }
        }
        list AssociatedDevice {
          key "MACAddress";
          config false;
          description
          "This table contains information about PLC connections
          running between this UPA interface and other UPA
          devices.";
          leaf MACAddress {
            config false;
            description
            "Remote UPA device MAC address.";
            type yang:mac-address;
          }
          leaf Port {
            config false;
            description
            "The PLC port number.";
            type uint32 {
              range "0..65535";
            }
          }
          leaf LogicalNetwork {
            config false;
            description
            "In the case where the associated device belongs to
            a different powerline network than the UPA
            interface, the actual network identifier of the
            neighboring network is not shown in {{param}}.
            Rather, only a generic string, e.g.  \"Network 1\",
            \"Network 2\", etc is stored here due to
            security/privacy implications.";
            type string {
              length "0..20";
            }
          }
          leaf PhyTxThroughput {
            config false;
            description
            "Physical transmission throughput (in {{units}}).";
            type uint32;
          }
          leaf PhyRxThroughput {
            config false;
            description
            "Physical reception throughput (in {{units}}).";
            type uint32;
          }
          leaf RealPhyRxThroughput {
            config false;
            description
            "Real Physical reception throughput (in {{units}}).";
            type uint32;
          }
          leaf EstimatedPLR {
            config false;
            description
            "Estimated PDU Loss Rate measurement between two
            devices (i.e.  estimated {{units}} of MPDUs that
            have been  received with errors).";
            type uint32 {
              range "0..100";
            }
          }
          leaf MeanEstimatedAtt {
            config false;
            description
            "Mean estimated attenuation (i.e.  channel loss
            between the local interface and the remote device).
            It is measured  in {{units}}.";
            type uint32;
          }
          leaf SmartRouteIntermediatePLCMAC {
            config false;
            description
            "Intermediate UPA adapter MAC address of the device
            that is acting as a relay to increase coverage in
            mesh scenarios.  This is the MAC address of a third
            UPA device, with which the UPA interface is doing
            smart repeating in order to transmit data to the
            associated {{param|MACAddress}} UPA device.
            {{param}} will be empty when {{param|DirectRoute}}
            is {{true}}.";
            type yang:mac-address;
          }
          leaf DirectRoute {
            config false;
            description
            "Route status, where {{true}} indicates ''direct''
            and {{false}} indicates ''indirect''.";
            type boolean;
          }
          leaf Active {
            config false;
            description
            "The ability to list inactive nodes is OPTIONAL.  If
            the CPE includes inactive nodes in this table,
            {{param}} MUST be set to {{false}}  for each
            inactive node.  The length of time an inactive node
            remains listed in this table is a local matter to
            the CPE.";
            type boolean;
          }
        }
        list ActiveNotch {
          key "Alias";
          config true;
          description
          "Note: All {{object}} entries can be enabled/disabled
          as a group using the {{param|#.ActiveNotchEnable}}
          parameter.";
          leaf Enable {
            config true;
            description
            "Enables or disables the active notch entry.";
            type boolean;
            default "false";
          }
          leaf Alias {
            config true;
            description
            "{{datatype|expand}}";
            type Alias;
          }
          leaf StartFreq {
            config true;
            description
            "The initial frequency (in {{units}}) of a notch
            enabled in the spectrum of the local interface.";
            type uint32;
          }
          leaf StopFreq {
            config true;
            description
            "The final frequency (in {{units}}) of a notch
            enabled in the spectrum of the local interface.";
            type uint32;
          }
          leaf Depth {
            config true;
            description
            "The depth (in {{units}}) of a notch enabled in the
            spectrum of the local interface.";
            type uint32;
          }
        }
        list BridgeFor {
          key "MACAddress";
          unique "Alias";
          config true;
          description
          "It shows the MAC addresses of the remote UPA devices
          with their associated port number, and the MAC
          addresses of the end-devices (PCs, STBs, routers,
          etc) connected to Ethernet port of the powerline
          adapters with their associated logical port.  In this
          way the system identifies to which UPA device an
          external device is connected to.";
          leaf Alias {
            config true;
            description
            "{{datatype|expand}}";
            type Alias;
          }
          leaf MACAddress {
            config true;
            description
            "MAC address of the device.";
            type yang:mac-address;
          }
          leaf Port {
            config false;
            description
            "Internal bridge associated port.";
            type uint32 {
              range "0..65535";
            }
          }
        }
      }
      container Diagnostics {
        description
        "The UPA Diagnostics object.";
        container InterfaceMeasurement {
          description
          "CFR and SNR measurements are done between a two UPA
          devices (a local interface and a remote device
          belonging to the same network).";
          leaf DiagnosticsState {
            config true;
            description
            "{{datatype|expand}}";
            type DiagnosticsState;
          }
          leaf Type {
            config true;
            description
            "Indicates the type of port measurement test to be
            carried out.  {{enum}}.";
            type enumeration {
              enum "SNR" {
                description
                "Signal-to-Noise-Ratio";
              }
              enum "CFR" {
                description
                "Channel Frequency Response";
              }
            }
          }
          leaf Interface {
            config true;
            description
            "{{reference}}  This is the local UPA interface from
            which the test is to be performed.";
            type string {
              length "0..256";
            }
          }
          leaf Port {
            config true;
            description
            "PLC port being measured.  This identifies which PLC
            connection to measure between the local interface
            (indicated by {{param|Interface}}) and the remote
            device (implied by {{param}}).";
            type uint32 {
              range "0..65535";
            }
          }
          leaf-list Measurements {
            config false;
            description
            "List items indicate measurements per carrier for a
            PLC port (expressed in {{units}}).";
            type uint32;
          }
          leaf RxGain {
            config false;
            description
            "Reception gain of the adapter (expresssed in
            {{units}}).";
            type int32;
          }
        }
      }
    }
    container WiFi {
      description
      "The WiFi object is based on the WiFi Alliance 802.11
      specifications ({{bibref|802.11-2007}}). It defines
      interface objects ({{object|Radio}} and {{object|SSID}}),
      and application objects ({{object|AccessPoint}} and
      {{object|EndPoint}}).";
      leaf RadioNumberOfEntries {
        config false;
        description
        "{{numentries}}";
        type uint32;
      }
      leaf SSIDNumberOfEntries {
        config false;
        description
        "{{numentries}}";
        type uint32;
      }
      leaf AccessPointNumberOfEntries {
        config false;
        description
        "{{numentries}}";
        type uint32;
      }
      leaf EndPointNumberOfEntries {
        config false;
        description
        "{{numentries}}";
        type uint32;
      }
      leaf ResetCounter {
        config false;
        description
        "This parameter counts the number of WiFi host or driver
        resets since the last device reset.  This parameter is
        reset to zero after the device resets, and increments
        with each successive WiFi host or driver reset.";
        type yang:counter32;
      }
      leaf Reset {
        config true;
        description
        "This parameter represents a request to reset or reboot
        the WiFi sub-system without resetting or rebooting the
        device.";
        type boolean;
      }
      list Radio {
        key "Name";
        unique "Alias";
        config true;
        description
        "Note: A dual-band single-radio device (e.g.  an
        802.11a/b/g radio) can be configured to operate at 2.4
        or 5 GHz frequency bands, but only a single frequency
        band is used to transmit/receive at a given time.
        Therefore, a single {{object}} instance is used even
        for a dual-band radio.";
        leaf Enable {
          config true;
          description
          "This parameter is based on ''ifAdminStatus'' from
          {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config true;
          description
          "The textual name of the radio as assigned by the CPE.";
          type string {
            length "0..64";
          }
        }
        leaf LastChange {
          config false;
          description
          "The accumulated time in {{units}} since the radio
          entered its current operational state.";
          type uint32;
        }
        leaf-list LowerLayers {
          config true;
          description
          "Note: Since {{object}} is a layer 1 interface, it is
          expected that {{param}} will not be used.";
          type string;
        }
        leaf Upstream {
          config false;
          description
          "This parameter is DEPRECATED because it gives a wrong
          indication for multiple SSIDs.  Use the
          {{param|#.SSID.{i}.Upstream}} parameter instead.";
          type boolean;
        }
        leaf MaxBitRate {
          config false;
          description
          "The maximum PHY bit rate supported by this interface
          (expressed in {{units}}).";
          type uint32;
        }
        leaf-list SupportedFrequencyBands {
          config false;
          description
          "{{list}} List items indicate the frequency bands at
          which the radio can operate.";
          type enumeration {
            enum "2.4GHz";
            enum "5GHz";
          }
        }
        leaf OperatingFrequencyBand {
          config true;
          description
          "If the radio supports multiple bands, and {{param}}
          is changed, then all parameters whose value is not
          valid for the new frequency band (e.g.
          {{param|Channel}}) MUST be set to a valid value
          (according to some CPE vendor-specific behavior).";
          type string;
          must ". = ../SupportedFrequencyBands";
        }
        leaf-list SupportedStandards {
          config false;
          description
          "If {{param|OperatingFrequencyBand}} is set to
          {{enum|5GHz|OperatingFrequencyBand}}, only values
          {{enum|a}}, {{enum|n}}, {{enum|ac}} are allowed.";
          type enumeration {
            enum "a" {
              description
              "{{bibref|802.11a-1999}}";
            }
            enum "b" {
              description
              "{{bibref|802.11b-1999}}";
            }
            enum "g" {
              description
              "{{bibref|802.11g-2003}}";
            }
            enum "n" {
              description
              "{{bibref|802.11n-2009}}";
            }
            enum "ac" {
              description
              "{{bibref|802.11ac-2013}}";
            }
          }
        }
        leaf-list OperatingStandards {
          config true;
          description
          "For example, a value of \"g,b\" (or \"b,g\" - order
          is not important) means that the 802.11g standard
          {{bibref|802.11g-2003}} is used with a
          backwards-compatible mode for 802.11b
          {{bibref|802.11b-1999}}. A value of \"g\" means that
          only the 802.11g standard can be used.";
          type string;
          must ". = ../SupportedStandards";
        }
        leaf-list PossibleChannels {
          config false;
          description
          "For example, for 802.11b and North America, would be
          \"1-11\".";
          type string;
        }
        leaf-list ChannelsInUse {
          config false;
          description
          "Ranges in the form \"n-m\" are permitted.";
          type string;
        }
        leaf Channel {
          config true;
          description
          "Note: Valid {{param}} values depend on the
          {{param|OperatingFrequencyBand}} and
          {{param|RegulatoryDomain}} values specified.";
          type uint32 {
            range "1..255";
          }
        }
        leaf AutoChannelSupported {
          config false;
          description
          "Indicates whether automatic channel selection is
          supported by this radio.  If {{false}}, then
          {{param|AutoChannelEnable}} MUST be {{false}}.";
          type boolean;
        }
        leaf AutoChannelEnable {
          config true;
          description
          "Whenever {{param}} is {{true}}, the value of the
          {{param|Channel}} parameter MUST be the channel
          selected by the automatic channel selection
          procedure.";
          type boolean;
        }
        leaf AutoChannelRefreshPeriod {
          config true;
          description
          "This parameter is significant only if
          {{param|AutoChannelEnable}} is set to {{true}}.";
          type uint32;
        }
        leaf ChannelLastChange {
          config false;
          description
          "The accumulated time in {{units}} since the current
          {{param|Channel}} came into use.";
          type uint32;
        }
        leaf ChannelLastSelectionReason {
          config false;
          description
          "The cause of the last channel selection.";
          type enumeration {
            enum "Manual" {
              description
              "Manual selection of the {{param|Channel}}.";
            }
            enum "Auto_Startup" {
              description
              "Automatic channel selection procedure launched at
              radio startup.";
            }
            enum "Auto_User" {
              description
              "Automatic channel selection procedure triggered
              by the user (e.g.  via a GUI).";
            }
            enum "Auto_Refresh" {
              description
              "Automatic channel selection procedure triggered
              by the {{param|AutoChannelRefreshPeriod}} timer.";
            }
            enum "Auto_Dynamic" {
              description
              "Automatic channel selection procedure dynamically
              triggered to adjust to environmental
              interference.";
            }
            enum "Auto_DFS" {
              description
              "Automatic channel selection procedure triggered
              by Dynamic Frequency Selection (DFS)
              {{bibref|ETSIBRAN}}.";
            }
            enum "Unknown";
          }
        }
        leaf MaxSupportedSSIDs {
          config false;
          description
          "Maximum number of SSIDs supported on this radio.";
          type uint32 {
            range "1..max";
          }
        }
        leaf MaxSupportedAssociations {
          config false;
          description
          "Maximum number of associated devices supported.";
          type uint32 {
            range "1..max";
          }
        }
        leaf FirmwareVersion {
          config false;
          description
          "This radio's WiFi firmware version.";
          type string {
            length "0..64";
          }
        }
        leaf-list SupportedOperatingChannelBandwidths {
          config false;
          description
          "{{list}}  These are the valid writable values for
          {{param|OperatingChannelBandwidth}}.";
          type enumeration {
            enum "20MHz";
            enum "40MHz" {
              description
              "wide mode";
            }
            enum "80MHz" {
              description
              "802.11ac only";
            }
            enum "160MHz" {
              description
              "802.11ac only";
            }
            enum "Auto";
          }
        }
        leaf OperatingChannelBandwidth {
          config true;
          description
          "The preferred channel bandwidth to be used
          (applicable to 802.11n and 802.11ac specifications
          only).";
          type string;
          must ". = ../SupportedOperatingChannelBandwidths";
        }
        leaf CurrentOperatingChannelBandwidth {
          config false;
          description
          "The channel bandwidth currently in use.";
          type enumeration {
            enum "20MHz";
            enum "40MHz";
            enum "80MHz";
            enum "160MHz";
          }
        }
        leaf ExtensionChannel {
          config true;
          description
          "The secondary extension channel position, applicable
          when operating in wide channel mode (i.e.  when
          {{param|OperatingChannelBandwidth}} is set to
          {{enum|40MHz|OperatingChannelBandwidth}} or
          {{enum|Auto|OperatingChannelBandwidth}}).";
          type enumeration {
            enum "AboveControlChannel";
            enum "BelowControlChannel";
            enum "Auto";
          }
        }
        leaf GuardInterval {
          config true;
          description
          "The guard interval value between OFDM symbols
          (applicable to 802.11n and 802.11ac specifications
          only).";
          type enumeration {
            enum "400nsec";
            enum "800nsec";
            enum "Auto";
          }
        }
        leaf MCS {
          config true;
          description
          "The Modulation Coding Scheme index (applicable to
          802.11n and 802.11ac specifications only). Values
          from 0 to 15 MUST be supported
          ({{bibref|802.11n-2009}}). Values from 0 to 9 MUST be
          supported for {{bibref|802.11ac-2013}}.  A value of
          -1 indicates automatic selection of the MCS index.";
          type int32 {
            range "-1..15|16..31";
          }
        }
        leaf-list TransmitPowerSupported {
          config false;
          description
          "A -1 item indicates auto mode (automatic decision by
          CPE). Auto mode allows the ''Radio'' to adjust
          transmit power accordingly.  For example, this can be
          useful for power-save modes such as EU-CoC, where the
          ''Radio'' can adjust power according to activity in
          the CPE.";
          type int32 {
            range "-1..100";
          }
        }
        leaf TransmitPower {
          config true;
          description
          "Indicates the current transmit power level as a
          {{units}} of full power.  The value MUST be one of
          the values reported by the
          {{param|TransmitPowerSupported}} parameter.  A value
          of -1 indicates auto mode (automatic decision by
          CPE).";
          type int32 {
            range "-1..100";
          }
        }
        leaf IEEE80211hSupported {
          config false;
          description
          "Indicates whether IEEE 802.11h
          {{bibref|802.11h-2003}} functionality is supported by
          this radio.  The value can be {{true}} only if the
          802.11a or the 802.11n@5GHz standard is supported
          (i.e.  {{param|SupportedFrequencyBands}} includes
          {{enum|5GHz|SupportedFrequencyBands}} and
          {{param|SupportedStandards}} includes
          {{enum|a|SupportedStandards}} and/or
          {{enum|n|SupportedStandards}}).";
          type boolean;
        }
        leaf IEEE80211hEnabled {
          config true;
          description
          "Indicates whether IEEE 802.11h functionality is
          enabled on this radio.  The value can be {{true}}
          only if the 802.11a or the 802.11n@5GHz standard is
          supported and enabled (i.e.
          {{param|OperatingFrequencyBand}} is
          {{enum|5GHz|OperatingFrequencyBand}} and
          {{param|OperatingStandards}} includes
          {{enum|a|OperatingStandards}} and/or
          {{enum|n|OperatingStandards}}).";
          type boolean;
        }
        leaf RegulatoryDomain {
          config true;
          description
          "The 802.11d Regulatory Domain.  First two octets are
          {{bibref|ISO3166-1}} two-character country code.  The
          third octet is either \" \" (all environments), \"O\"
          (outside) or \"I\" (inside).";
          type string {
            length "3";
            pattern "[A-Z][A-Z][ OI]";
          }
        }
        leaf RetryLimit {
          config true;
          description
          "The maximum number of retransmissions of a short
          packet i.e.  a packet that is no longer than the
          {{param|RTSThreshold}}. This corresponds to IEEE
          802.11 parameter ''dot11ShortRetryLimit''
          {{bibref|802.11-2012}}.";
          type uint32 {
            range "0..7";
          }
        }
        leaf CCARequest {
          config true;
          description
          "A request for the clear channel assessment (CCA)
          report in the format specified in
          {{bibref|802.11-2012|Clause 8.4.2.23.3}}.";
          type yang:hex-string {
            length "11";
          }
        }
        leaf CCAReport {
          config false;
          description
          "If this parameter is read before a CCARequest has
          been issued, then its value is {{empty}}.";
          type yang:hex-string {
            length "12";
          }
        }
        leaf RPIHistogramRequest {
          config true;
          description
          "A request for a received power indicator (RPI)
          histogram in the format specified in
          {{bibref|802.11-2012|Clause 8.4.2.23.4}}.";
          type yang:hex-string {
            length "11";
          }
        }
        leaf RPIHistogramReport {
          config false;
          description
          "Received power indicator (RPI) histogram report in
          the format specified in {{bibref|802.11-2012|Clause
          8.4.2.24.4}}.";
          type yang:hex-string {
            length "19";
          }
        }
        leaf FragmentationThreshold {
          config true;
          description
          "This specifies the current maximum size, in
          {{units}}, of the MPDU that can be delivered to the
          PHY. This parameter is based on
          ''dot11FragmentationThreshold'' from
          {{bibref|802.11-2012}}.";
          type uint32;
        }
        leaf RTSThreshold {
          config true;
          description
          "This indicates the number of {{units}} in an MPDU,
          below which an RTS/CTS handshake is not performed.
          This parameter is based on ''dot11RTSThreshold'' from
          {{bibref|802.11-2012}}.";
          type uint32;
        }
        leaf LongRetryLimit {
          config true;
          description
          "This indicates the maximum number of transmission
          attempts of a frame, the length of which is greater
          than {{param|RTSThreshold}}, that will be made before
          a failure condition is indicated.  This parameter is
          based on ''dot11LongRetryLimit'' from
          {{bibref|802.11-2012}}.";
          type uint32;
        }
        leaf BeaconPeriod {
          config true;
          description
          "Time interval between transmitting beacons (expressed
          in {{units}}). This parameter is based on
          ''dot11BeaconPeriod'' from {{bibref|802.11-2012}}.";
          type uint32;
        }
        leaf DTIMPeriod {
          config true;
          description
          "This specifies the number of beacon intervals that
          elapse between transmission of Beacon frames
          containing a TIM element whose DTIM Count field is 0.
          This parameter is based on ''dot11DTIMPeriod'' from
          {{bibref|802.11-2012}}.";
          type uint32;
        }
        leaf PacketAggregationEnable {
          config true;
          description
          "This determines whether or not packet aggregation
          (commonly called \"frame aggregation\") is enabled.
          This applies only to 802.11n.";
          type boolean;
        }
        leaf PreambleType {
          config true;
          description
          "The type of preamble.  Longer preambles (more
          overhead) are needed by 802.11g to coexist with
          legacy systems 802.11 and 802.11b.";
          type enumeration {
            enum "short";
            enum "long";
            enum "auto";
          }
        }
        leaf-list BasicDataTransmitRates {
          config true;
          description
          "{{list}} The set of data rates, in ''Mbps'', that
          have to be supported by all stations that desire to
          join this BSS. The stations have to be able to
          receive and transmit at each of the data rates listed
          in {{param}}. For example, a value of \"1,2\",
          indicates that stations support 1 Mbps and 2 Mbps.
          Most control packets use a data rate in {{param}}.";
          type string;
        }
        leaf-list OperationalDataTransmitRates {
          config true;
          description
          "{{list}} Maximum access point data transmit rates in
          ''Mbps'' for unicast frames (a superset of
          {{param|BasicDataTransmitRates}}). Given the value of
          {{param|BasicDataTransmitRates}} from the example
          above, {{param}} might be \"1,2,5.5,11\", indicating
          that unicast frames can additionally be transmitted
          at 5.5 Mbps and 11 Mbps.";
          type string;
        }
        leaf-list SupportedDataTransmitRates {
          config false;
          description
          "{{list}} Data transmit rates in ''Mbps'' for unicast
          frames at which the access point will permit a
          station to connect (a subset of
          {{param|OperationalDataTransmitRates}}). Given the
          values of {{param|BasicDataTransmitRates}} and
          {{param|OperationalDataTransmitRates}} from the
          examples above, {{param}} might be \"1,2,5.5\",
          indicating that the AP will only permit connections
          at 1 Mbps, 2 Mbps and 5.5 Mbps, even though it could
          theoretically accept connections at 11 Mbps.";
          type string;
        }
        container Stats {
          description
          "Throughput statistics for this interface.  Packet
          counters here count 802.11 WiFi frames.  See
          {{bibref|TR-181i2a5|Appendix III}} for further
          details.  The CPE MUST reset the interface's Stats
          parameters (unless otherwise stated in individual
          object or parameter descriptions) either when the
          interface becomes operationally down due to a
          previous administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2a5|Section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf PLCPErrorCount {
            config false;
            description
            "The number of packets that were received with a
            detected Physical Layer Convergence Protocol (PLCP)
            header error.";
            type uint32;
          }
          leaf FCSErrorCount {
            config false;
            description
            "The number of packets that were received with a
            detected FCS error.  This parameter is based on
            dot11FCSErrorCount from {{bibref|802.11-2012|Annex
            C}}.";
            type uint32;
          }
          leaf InvalidMACCount {
            config false;
            description
            "The number of packets that were received with a
            detected invalid MAC header error.";
            type uint32;
          }
          leaf PacketsOtherReceived {
            config false;
            description
            "The number of packets that were received, but which
            were destined for a MAC address that is not
            associated with this interface.";
            type uint32;
          }
          leaf Noise {
            config false;
            description
            "An indicator of average noise strength received at
            this radio, measured in {{units}}. This measurement
            of non-IEEE 802.11 noise power is made by sampling
            the channel when virtual carrier sense indicates
            idle and this radio is neither transmitting nor
            receiving a frame.";
            type int32;
          }
          leaf TotalChannelChangeCount {
            config false;
            description
            "The total number of times that the
            {{param|#.Channel}} has changed since the
            {{object|.WiFi.Radio}} entered its current
            operating state.";
            type uint32;
          }
          leaf ManualChannelChangeCount {
            config false;
            description
            "The number of times that the {{param|#.Channel}}
            has changed due to manual channel selection since
            the {{object|.WiFi.Radio}} entered its current
            operating state.";
            type uint32;
          }
          leaf AutoStartupChannelChangeCount {
            config false;
            description
            "The number of times that the {{param|#.Channel}}
            has changed due to automatic channel selection
            procedure launched at radio startup since the
            {{object|.WiFi.Radio}} entered its current
            operating state.";
            type uint32;
          }
          leaf AutoUserChannelChangeCount {
            config false;
            description
            "The number of times that the {{param|#.Channel}}
            has changed due to automatic channel selection
            procedure triggered by the user (e.g.  via a GUI)
            since the {{object|.WiFi.Radio}} entered its
            current operating state.";
            type uint32;
          }
          leaf AutoRefreshChannelChangeCount {
            config false;
            description
            "The number of times that the {{param|#.Channel}}
            has changed due to automatic channel selection
            procedure triggered by the
            {{param|#.AutoChannelRefreshPeriod}} timer since
            the {{object|.WiFi.Radio}} entered its current
            operating state.";
            type uint32;
          }
          leaf AutoDynamicChannelChangeCount {
            config false;
            description
            "The number of times that the {{param|#.Channel}}
            has changed due to automatic channel selection
            procedure dynamically triggered to adjust to
            environmental interference since the
            {{object|.WiFi.Radio}} entered its current
            operating state.";
            type uint32;
          }
          leaf AutoDFSChannelChangeCount {
            config false;
            description
            "The number of times that the {{param|#.Channel}}
            has changed due to automatic channel selection
            procedure triggered by DFS {{bibref|ETSIBRAN}}
            since the {{object|.WiFi.Radio}} entered its
            current operating state.";
            type uint32;
          }
        }
      }
      container NeighboringWiFiDiagnostic {
        description
        "This object defines access to other WiFi SSIDs that
        this device is able to receive.";
        leaf DiagnosticsState {
          config true;
          description
          "{{datatype|expand}}";
          type DiagnosticsState;
        }
        leaf ResultNumberOfEntries {
          config false;
          description
          "{{numentries}}";
          type uint32;
        }
        list Result {
          key "BSSID";
          config false;
          description
          "Neighboring SSID table.  This table models the other
          WiFi SSIDs that this device is able to receive.";
          leaf Radio {
            config false;
            description
            "The Radio that detected the neighboring WiFi SSID.";
            type string;
          }
          leaf SSID {
            config false;
            description
            "The current service set identifier in use by the
            neighboring WiFi SSID. The value MAY be empty for
            hidden SSIDs.";
            type string {
              length "0..32";
            }
          }
          leaf BSSID {
            config false;
            description
            "The BSSID used for the neighboring WiFi SSID.";
            type yang:mac-address;
          }
          leaf Mode {
            config false;
            description
            "The mode the neighboring WiFi radio is operating
            in.";
            type enumeration {
              enum "AdHoc";
              enum "Infrastructure";
            }
          }
          leaf Channel {
            config false;
            description
            "The current radio channel used by the neighboring
            WiFi radio.";
            type uint32 {
              range "1..255";
            }
          }
          leaf SignalStrength {
            config false;
            description
            "An indicator of radio signal strength (RSSI) of the
            neighboring WiFi radio measured in {{units}}, as an
            average of the last 100 packets received.";
            type int32 {
              range "-200..0";
            }
          }
          leaf SecurityModeEnabled {
            config false;
            description
            "The type of encryption the neighboring WiFi SSID
            advertises.";
            type enumeration {
              enum "None";
              enum "WEP";
              enum "WPA";
              enum "WPA2";
              enum "WPA-WPA2";
              enum "WPA-Enterprise";
              enum "WPA2-Enterprise";
              enum "WPA-WPA2-Enterprise";
            }
          }
          leaf-list EncryptionMode {
            config false;
            description
            "The type of encryption the neighboring WiFi SSID
            advertises.";
            type enumeration {
              enum "TKIP";
              enum "AES";
            }
          }
          leaf OperatingFrequencyBand {
            config false;
            description
            "Indicates the frequency band at which the radio
            this SSID instance is operating.";
            type enumeration {
              enum "2.4GHz";
              enum "5GHz";
            }
          }
          leaf-list SupportedStandards {
            config false;
            description
            "If {{param|OperatingFrequencyBand}} is set to
            {{enum|5GHz|OperatingFrequencyBand}}, only values
            {{enum|a}}, {{enum|n}}, {{enum|ac}} are allowed.";
            type enumeration {
              enum "a" {
                description
                "{{bibref|802.11a-1999}}";
              }
              enum "b" {
                description
                "{{bibref|802.11b-1999}}";
              }
              enum "g" {
                description
                "{{bibref|802.11g-2003}}";
              }
              enum "n" {
                description
                "{{bibref|802.11n-2009}}";
              }
              enum "ac" {
                description
                "{{bibref|802.11ac-2013}}";
              }
            }
          }
          leaf-list OperatingStandards {
            config false;
            description
            "For example, a value of \"g,b\" (or \"b,g\" - order
            is not important) means that the 802.11g standard
            {{bibref|802.11g-2003}} is used with a
            backwards-compatible mode for 802.11b
            {{bibref|802.11b-1999}}. A value of \"g\" means
            that only the 802.11g standard can be used.";
            type string;
            must ". = ../SupportedStandards";
          }
          leaf OperatingChannelBandwidth {
            config false;
            description
            "Indicates the bandwidth at which the channel is
            operating.";
            type enumeration {
              enum "20MHz";
              enum "40MHz";
              enum "80MHz";
              enum "160MHz";
              enum "Auto";
            }
          }
          leaf BeaconPeriod {
            config false;
            description
            "Time interval (in {{units}}) between transmitting
            beacons.";
            type uint32;
          }
          leaf Noise {
            config false;
            description
            "Indicator of average noise strength (in {{units}})
            received from the neighboring WiFi radio.";
            type int32 {
              range "-200..0";
            }
          }
          leaf-list BasicDataTransferRates {
            config false;
            description
            "{{list}} Basic data transmit rates (in Mbps) for
            the SSID.  For example, if {{param}} is \"1,2\",
            this indicates that the SSID is operating with
            basic rates of 1 Mbps and 2 Mbps.";
            type string;
          }
          leaf-list SupportedDataTransferRates {
            config false;
            description
            "{{list}} Data transmit rates (in Mbps) for unicast
            frames at which the SSID will permit a station to
            connect.  For example, if {{param}} is \"1,2,5.5\",
            this indicates that the SSID will only permit
            connections at 1 Mbps, 2 Mbps and 5.5 Mbps.";
            type string;
          }
          leaf DTIMPeriod {
            config false;
            description
            "The number of beacon intervals that elapse between
            transmission of Beacon frames containing a TIM
            element whose DTIM count field is 0. This value is
            transmitted in the DTIM Period field of beacon
            frames.  {{bibref|802.11-2012}}";
            type uint32;
          }
        }
      }
      list SSID {
        key "BSSID";
        unique "Alias";
        unique "Name";
        config true;
        description
        "WiFi SSID is also a multiplexing layer, i.e.  more than
        one {{object}} can be stacked above a single
        {{object|#.Radio}}.";
        leaf Enable {
          config true;
          description
          "This parameter is based on ''ifAdminStatus'' from
          {{bibref|RFC2863}}.";
          type boolean;
          default "false";
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
          default "Down";
        }
        leaf Alias {
          config true;
          description
          "{{datatype|expand}}";
          type Alias;
        }
        leaf Name {
          config false;
          description
          "The textual name of the SSID entry as assigned by the
          CPE.";
          type string {
            length "0..64";
          }
        }
        leaf LastChange {
          config false;
          description
          "The accumulated time in {{units}} since the SSID
          entered its current operational state.";
          type uint32;
        }
        leaf-list LowerLayers {
          config true;
          description
          "{{list}} {{reference|an interface object that is
          stacked immediately below this interface object}}
          See {{bibref|TR-181i2|Section 4.2.1}}.";
          type string;
        }
        leaf BSSID {
          config true;
          description
          "This is the MAC address of the access point, which
          can either be local (when this instance models an
          access point SSID) or remote (when this instance
          models an end point SSID).";
          type yang:mac-address;
        }
        leaf MACAddress {
          config false;
          description
          "Note: This is not necessarily the same as the
          Ethernet header source or destination MAC address,
          which is associated with the IP interface and is
          modeled via the
          {{param|.Ethernet.Link.{i}.MACAddress}} parameter.";
          type yang:mac-address;
        }
        leaf SSID {
          config true;
          description
          "The current service set identifier in use by the
          connection.  The SSID is an identifier that is
          attached to packets sent over the wireless LAN that
          functions as an ID for joining a particular radio
          network (BSS).";
          type string {
            length "0..32";
          }
        }
        leaf Upstream {
          config false;
          description
          "This parameter supersedes the deprecated
          {{param|#.Radio.{i}.Upstream}} parameter.  If both
          exist, the parameter {{param|#.Radio.{i}.Upstream}}
          is ignored.";
          type boolean;
        }
        container Stats {
          description
          "Throughput statistics for this interface.  Packet
          counters here count 802.11 WiFi frames.  See
          {{bibref|TR-181i2a5|Appendix III}} for further
          details.  The CPE MUST reset the interface's Stats
          parameters (unless otherwise stated in individual
          object or parameter descriptions) either when the
          interface becomes operationally down due to a
          previous administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2a5|Section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.  These can be due
            to the number of retransmissions exceeding the
            retry limit, or from other causes.";
            type uint32;
          }
          leaf RetransCount {
            config false;
            description
            "The total number of transmitted packets which were
            retransmissions.  Two retransmissions of the same
            packet results in this counter incrementing by two.";
            type uint32;
          }
          leaf FailedRetransCount {
            config false;
            description
            "The number of packets that were not transmitted
            successfully due to the number of retransmission
            attempts exceeding an 802.11 retry limit.  This
            parameter is based on dot11FailedCount from
            {{bibref|802.11-2012}}.";
            type uint32;
          }
          leaf RetryCount {
            config false;
            description
            "The number of packets that were successfully
            transmitted after one or more retransmissions.
            This parameter is based on dot11RetryCount from
            {{bibref|802.11-2012}}.";
            type uint32;
          }
          leaf MultipleRetryCount {
            config false;
            description
            "The number of packets that were successfully
            transmitted after more than one retransmission.
            This parameter is based on dot11MultipleRetryCount
            from {{bibref|802.11-2012}}.";
            type uint32;
          }
          leaf ACKFailureCount {
            config false;
            description
            "The number of expected ACKs that were never
            received.  This parameter is based on
            dot11ACKFailureCount from {{bibref|802.11-2012}}.";
            type uint32;
          }
          leaf AggregatedPacketCount {
            config false;
            description
            "The number of aggregated packets that were
            transmitted.  This applies only to 802.11n and
            802.11ac.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "The total number of packets that higher-level
            protocols requested for transmission and which were
            addressed to a broadcast address at this layer,
            including those that were discarded or not sent.";
            type uint64;
          }
          leaf BroadcastPacketsReceived {
            config false;
            description
            "The total number of received packets, delivered by
            this layer to a higher layer, which were addressed
            to a broadcast address at this layer.";
            type uint64;
          }
          leaf UnknownProtoPacketsReceived {
            config false;
            description
            "The total number of packets received via the
            interface which were discarded because of an
            unknown or unsupported  protocol.";
            type uint32;
          }
        }
      }
      list AccessPoint {
        key "SSIDReference";
        unique "Alias";
        config true;
        description
        "Note: The {{object}} table includes a unique key
        parameter that is a strong reference.  If a strongly
        referenced object is deleted, the CPE will set the
        referencing parameter to {{empty}}. However, doing so
        under these circumstances might cause the updated
        {{object}} row to then violate the table's unique key
        constraint; if this occurs, the CPE MUST set
        {{param|Status}} to {{enum|Error_Misconfigured|Status}}
        and disable the offending {{object}} row.";
        leaf Enable {
          config true;
          description
          "Enables or disables this access point.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Alias {
          config true;
          description
          "{{datatype|expand}}";
          type Alias;
        }
        leaf SSIDReference {
          config true;
          description
          "{{reference}}";
          type string {
            length "0..256";
          }
        }
        leaf SSIDAdvertisementEnabled {
          config true;
          description
          "Indicates whether or not beacons include the SSID
          name.";
          type boolean;
        }
        leaf RetryLimit {
          config true;
          description
          "This parameter is DEPRECATED because it is really a
          {{object|#.Radio}} attribute.  Use
          {{param|#.Radio.{i}.RetryLimit}}.";
          type uint32 {
            range "0..7";
          }
        }
        leaf WMMCapability {
          config false;
          description
          "Indicates whether this access point supports WiFi
          Multimedia (WMM) Access Categories (AC).";
          type boolean;
        }
        leaf UAPSDCapability {
          config false;
          description
          "Note: U-APSD support implies WMM support.";
          type boolean;
        }
        leaf WMMEnable {
          config true;
          description
          "Whether WMM support is currently enabled.  When
          enabled, this is indicated in beacon frames.";
          type boolean;
        }
        leaf UAPSDEnable {
          config true;
          description
          "Note: U-APSD can only be enabled if WMM is also
          enabled.";
          type boolean;
        }
        leaf AssociatedDeviceNumberOfEntries {
          config false;
          description
          "{{numentries}}";
          type uint32;
        }
        leaf MaxAssociatedDevices {
          config true;
          description
          "A value of 0 means that there is no specific limit.";
          type uint32;
          default "0";
        }
        leaf IsolationEnable {
          config true;
          description
          "A value of {{true}} means that the devices connected
          to the Access Point are isolated from all other
          devices within the home network (as is typically the
          case for a Wireless Hotspot).";
          type boolean;
        }
        leaf MACAddressControlEnabled {
          config true;
          description
          "Indicates whether or not MAC Address Control is
          enabled on this {{object|#}}.  MAC Address Control
          limits client devices to those whose hardware
          addresses match the {{param|AllowedMACAddress}} list.";
          type boolean;
        }
        leaf-list AllowedMACAddress {
          config true;
          description
          "Hardware addresses of client devices that are allowed
          to associate with this {{object|#}} if
          {{param|MACAddressControlEnabled}} is {{true}}.";
          type yang:mac-address;
        }
        leaf MaxAllowedAssociations {
          config true;
          description
          "If the parameter
          {{param|#.Radio.{i}.MaxSupportedAssociations}}
          exists, the value MUST be less than or equal to the
          maximum number specified in
          {{param|#.Radio.{i}.MaxSupportedAssociations}}.";
          type uint32;
        }
        container Security {
          description
          "This object contains security related parameters that
          apply to a CPE acting as an Access Point
          {{bibref|802.11-2007}}.";
          leaf-list ModesSupported {
            config false;
            description
            "{{list}} Indicates which security modes this
            {{object|#}} instance is capable of supporting.";
            type enumeration {
              enum "None";
              enum "WEP-64";
              enum "WEP-128";
              enum "WPA-Personal";
              enum "WPA2-Personal";
              enum "WPA-WPA2-Personal";
              enum "WPA-Enterprise";
              enum "WPA2-Enterprise";
              enum "WPA-WPA2-Enterprise";
            }
          }
          leaf ModeEnabled {
            config true;
            description
            "Indicates which security mode is enabled.";
            type string;
            must ". = ../ModesSupported";
          }
          leaf WEPKey {
            config true;
            description
            "A 5 byte {{param}} corresponds to security mode
            {{enum|WEP-64|ModeEnabled}} and a 13 byte {{param}}
            corresponds to security mode
            {{enum|WEP-128|ModeEnabled}}.";
            type yang:hex-string {
              length "5|13";
            }
          }
          leaf PreSharedKey {
            config true;
            description
            "If {{param|KeyPassphrase}} is written, then
            {{param}} is immediately generated.  The ACS SHOULD
            NOT set both the {{param|KeyPassphrase}} and the
            {{param}} directly (the result of doing this is
            undefined).";
            type yang:hex-string {
              length "0..32";
            }
          }
          leaf KeyPassphrase {
            config true;
            description
            "If {{param}} is written, then
            {{param|PreSharedKey}} is immediately generated.
            The ACS SHOULD NOT set both the {{param}} and the
            {{param|PreSharedKey}} directly (the result of
            doing this is undefined). The key is generated as
            specified by WPA, which uses PBKDF2 from PKCS #5:
            Password-based Cryptography Specification Version
            2.0 ({{bibref|RFC2898}}).";
            type string {
              length "8..63";
            }
          }
          leaf RekeyingInterval {
            config true;
            description
            "This is applicable to WPA, WPA2 and Mixed
            (WPA-WPA2) modes in Personal or Enterprise mode
            (i.e.  when {{param|ModeEnabled}} is set to a value
            other than {{enum|None|ModeEnabled}} or
            {{enum|WEP-64|ModeEnabled}} or
            {{enum|WEP-128|ModeEnabled}}.";
            type uint32;
            default "3600";
          }
          leaf RadiusServerIPAddr {
            config true;
            description
            "The IP Address of the RADIUS server used for WLAN
            security.  {{param}} is only applicable when
            {{param|ModeEnabled}} is an Enterprise type (i.e.
            {{enum|WPA-Enterprise|ModeEnabled}},
            {{enum|WPA2-Enterprise|ModeEnabled}} or
            {{enum|WPA-WPA2-Enterprise|ModeEnabled}}).";
            type inet:ip-address;
          }
          leaf SecondaryRadiusServerIPAddr {
            config true;
            description
            "The client can forward requests to the secondary
            server in the event that the primary server is down
            or unreachable, or after a number of tries to the
            primary server fail, or in a round-robin fashion
            {{bibref|RFC2865}}.";
            type inet:ip-address;
          }
          leaf RadiusServerPort {
            config true;
            description
            "The port number of the RADIUS server used for WLAN
            security.  {{param}} is only applicable when
            {{param|ModeEnabled}} is an Enterprise type (i.e.
            {{enum|WPA-Enterprise|ModeEnabled}},
            {{enum|WPA2-Enterprise|ModeEnabled}} or
            {{enum|WPA-WPA2-Enterprise|ModeEnabled}}).";
            type uint32;
            default "1812";
          }
          leaf SecondaryRadiusServerPort {
            config true;
            description
            "If this parameter is not implemented, the secondary
            RADIUS server will use the same port number as the
            primary RADIUS server.";
            type uint32;
            default "1812";
          }
          leaf RadiusSecret {
            config true;
            description
            "The secret used for handshaking with the RADIUS
            server {{bibref|RFC2865}}.";
            type string;
          }
          leaf SecondaryRadiusSecret {
            config true;
            description
            "If this parameter is not implemented, the secondary
            RADIUS server will use the same secret as the
            primary RADIUS server.";
            type string;
          }
          leaf MFPConfig {
            config true;
            description
            "Management Frame Protection configuration
            applicable when {{param|ModeEnabled}} is set to
            {{enum|WPA2-Personal|ModeEnabled}} or
            {{enum|WPA2-Enterprise|ModeEnabled}}.";
            type enumeration {
              enum "Disabled";
              enum "Optional";
              enum "Required";
            }
            default "Disabled";
          }
          leaf Reset {
            config true;
            description
            "If the parameter cannot be set, the CPE MUST reject
            the request as an invalid parameter value.
            Possible failure reasons include a lack of default
            values or if {{param|ModeEnabled}} is an Enterprise
            type, i.e.  {{enum|WPA-Enterprise|ModesSupported}},
            {{enum|WPA2-Enterprise|ModesSupported}} or
            {{enum|WPA-WPA2-Enterprise|ModesSupported}}.";
            type boolean;
          }
        }
        container WPS {
          description
          "This object contains parameters related to Wi-Fi
          Protected Setup for this access point (as specified
          in {{bibref|WPSv1.0}} or {bibref|WPSv2.0}}).";
          leaf Enable {
            config true;
            description
            "Enables or disables WPS functionality for this
            access point.";
            type boolean;
            default "true";
          }
          leaf-list ConfigMethodsSupported {
            config false;
            description
            "The {{enum|USBFlashDrive}} and {{enum|Ethernet}}
            are only applicable in WPS 1.0 and are deprecated
            in WPS 2.x.  The {{enum|PhysicalPushButton}},
            {{enum|VirtualPushButton}},
            {{enum|PhysicalDisplay}} and
            {{enum|VirtualDisplay}} are applicable to WPS 2.x
            only.";
            type enumeration {
              enum "USBFlashDrive";
              enum "Ethernet";
              enum "Label";
              enum "Display";
              enum "ExternalNFCToken";
              enum "IntegratedNFCToken";
              enum "NFCInterface";
              enum "PushButton";
              enum "PIN";
              enum "PhysicalPushButton";
              enum "PhysicalDisplay";
              enum "VirtualPushButton";
              enum "VirtualDisplay";
            }
          }
          leaf-list ConfigMethodsEnabled {
            config true;
            description
            "{{list}} Indicates WPS configuration methods
            enabled on the device.";
            type string;
            must ". = ../ConfigMethodsSupported";
          }
          leaf Status {
            config false;
            description
            "{{list}} Indicates the current status of WPS. If
            the device goes to {{enum|SetupLocked}} the WPS
            needs to be disabled and re-enabled to come out of
            state.";
            type enumeration {
              enum "Disabled";
              enum "Error";
              enum "Unconfigured";
              enum "Configured";
              enum "SetupLocked";
            }
          }
          leaf Version {
            config false;
            description
            "For example, a value of ''1.0'' denotes WSC 1.0 and
            a value of ''2.0'' denotes WSC 2.0.";
            type string;
          }
          leaf PIN {
            config true;
            description
            "{{hidden}}";
            type string {
              length "0..8";
              pattern "\\d{4}|\\d{8}";
            }
          }
        }
        list AssociatedDevice {
          key "MACAddress";
          config false;
          description
          "A table of the devices currently associated with the
          access point.";
          leaf MACAddress {
            config false;
            description
            "The MAC address of an associated device.";
            type yang:mac-address;
          }
          leaf OperatingStandard {
            config false;
            description
            "The operating standard that this associated device
            is connected with.";
            type enumeration {
              enum "a" {
                description
                "{{bibref|802.11a-1999}}";
              }
              enum "b" {
                description
                "{{bibref|802.11b-1999}}";
              }
              enum "g" {
                description
                "{{bibref|802.11g-2003}}";
              }
              enum "n" {
                description
                "{{bibref|802.11n-2009}}";
              }
              enum "ac" {
                description
                "{{bibref|802.11ac-2013}}";
              }
            }
          }
          leaf AuthenticationState {
            config false;
            description
            "Whether an associated device has authenticated
            ({{true}}) or not ({{false}}).";
            type boolean;
          }
          leaf LastDataDownlinkRate {
            config false;
            description
            "The data transmit rate in {{units}} that was most
            recently used for transmission from the access
            point to the associated device.";
            type uint32 {
              range "1000..max";
            }
          }
          leaf LastDataUplinkRate {
            config false;
            description
            "The data transmit rate in {{units}} that was most
            recently used for transmission from the associated
            device to the access point.";
            type uint32 {
              range "1000..max";
            }
          }
          leaf AssociationTime {
            config false;
            description
            "Date and time in UTC when the device was associated";
            type yang:date-and-time;
          }
          leaf SignalStrength {
            config false;
            description
            "An indicator of radio signal strength of the uplink
            from the associated device to the access point,
            measured in {{units}}, as an average of the last
            100 packets received from the device.";
            type int32 {
              range "-200..0";
            }
          }
          leaf Noise {
            config false;
            description
            "An indicator of radio noise on the uplink from the
            associated device to the access point, measured in
            {{units}}, as an average of the last 100 packets
            received from the device (see ANPI definition in
            {{bibref|802.11-2012|Clause 10.11.9.4}})";
            type int32 {
              range "-200..0";
            }
          }
          leaf Retransmissions {
            config false;
            description
            "The number of {{units}} that had to be
            re-transmitted, from the last 100 packets sent to
            the associated device.  Multiple re-transmissions
            of the same packet count as one.";
            type uint32 {
              range "0..100";
            }
          }
          leaf Active {
            config false;
            description
            "The ability to list inactive nodes is OPTIONAL. If
            the CPE includes inactive nodes in this table,
            {{param}} MUST be set to {{false}} for each
            inactive node.  The length of time an inactive node
            remains listed in this table is a local matter to
            the CPE.";
            type boolean;
          }
          container Stats {
            description
            "The CPE MUST reset these {{object}} parameters
            (unless otherwise stated in individual object or
            parameter descriptions) either when the
            {{param|##.Status}} of the parent {{object|##}}
            object transitions from {{enum|Disabled|##.Status}}
            to {{enum|Enabled|##.Status}}, or when it
            transitions from {{enum|Enabled|##.Status}} to
            {{enum|Disabled|##.Status}}.";
            leaf BytesSent {
              config false;
              description
              "The total number of bytes transmitted to the
              Associated Device, including framing characters.";
              type yang:counter32;
            }
            leaf BytesReceived {
              config false;
              description
              "The total number of bytes received from the
              Associated Device, including framing characters.";
              type yang:counter32;
            }
            leaf PacketsSent {
              config false;
              description
              "The total number of packets transmitted to the
              Associated Device.";
              type yang:counter32;
            }
            leaf PacketsReceived {
              config false;
              description
              "The total number of packets received from the
              Associated Device.";
              type yang:counter32;
            }
            leaf ErrorsSent {
              config false;
              description
              "The total number of outbound packets that could
              not be transmitted because of errors.  These
              might be due to the number of retransmissions
              exceeding the retry limit, or from other causes.";
              type yang:counter32;
            }
            leaf RetransCount {
              config false;
              description
              "The total number of transmitted packets which
              were retransmissions.  Two retransmissions of the
              same packet results in this counter incrementing
              by two.";
              type yang:counter32;
            }
            leaf FailedRetransCount {
              config false;
              description
              "The number of packets that were not transmitted
              successfully due to the number of retransmission
              attempts exceeding an 802.11 retry limit.  This
              parameter is based on ''dot11FailedCount'' from
              {{bibref|802.11-2012}}.";
              type yang:counter32;
            }
            leaf RetryCount {
              config false;
              description
              "The number of packets that were successfully
              transmitted after one or more retransmissions.
              This parameter is based on ''dot11RetryCount''
              from {{bibref|802.11-2012}}.";
              type yang:counter32;
            }
            leaf MultipleRetryCount {
              config false;
              description
              "The number of packets that were successfully
              transmitted after more than one retransmission.
              This parameter is based on
              ''dot11MultipleRetryCount'' from
              {{bibref|802.11-2012}}.";
              type yang:counter32;
            }
          }
        }
        list AC {
          key "AccessCategory";
          config true;
          description
          "* VO (Voice)";
          leaf AccessCategory {
            config true;
            description
            "This identifies the access category.";
            type enumeration {
              enum "BE";
              enum "BK";
              enum "VI";
              enum "VO";
            }
          }
          leaf Alias {
            config true;
            description
            "{{datatype|expand}}";
            type Alias;
          }
          leaf AIFSN {
            config true;
            description
            "Arbitration Inter Frame Spacing (Number). This is
            the number of time slots in the arbitration
            interframe space.";
            type uint32 {
              range "2..15";
            }
          }
          leaf ECWMin {
            config true;
            description
            "Exponent of Contention Window (Minimum). This
            encodes the values of CWMin as an exponent: CWMin =
            2^ECWMin - 1. For example, if ECWMin is 8, then
            CWMin is 2^8 - 1, or 255, (expressed in {{units}}).";
            type uint32 {
              range "0..15";
            }
          }
          leaf ECWMax {
            config true;
            description
            "Exponent of Contention Window (Maximum). This
            encodes the values of CWMax as an exponent: CWMax =
            2^ECWMax - 1. For example, if ECWMax is 8, then
            CWMax is 2^8 - 1, or 255, (expressed in {{units}}).";
            type uint32 {
              range "0..15";
            }
          }
          leaf TxOpMax {
            config true;
            description
            "Maximum transmit opportunity, in multiples of
            {{units}}. A TXOP time interval of 0 means it is
            limited to a single MAC protocol data unit (MPDU).";
            type uint32 {
              range "0..255";
            }
          }
          leaf AckPolicy {
            config true;
            description
            "Ack Policy, where False=\"Do Not Acknowledge\" and
            True=\"Acknowledge\"";
            type boolean;
          }
          leaf-list OutQLenHistogramIntervals {
            config true;
            description
            "{{list}} Definition of the histogram intervals for
            counting the transmit queue length in packets.
            Each value indicates the maximum value of the
            interval.  For example, \"0,1,4,8,\" defines the
            five intervals: 0 packets in queue, 1 packet in
            queue, 2 to 4 packets in queue, 5 to 8 packets in
            queue, and 9 or more packets in queue.  (No value
            after the last comma means no upper bound.) If this
            parameter is set to {{empty}}, no
            {{param|Stats.OutQLenHistogram}} stats will be
            collected.";
            type string;
          }
          leaf OutQLenHistogramSampleInterval {
            config true;
            description
            "The time between recording samples of the current
            transmit queue in {{units}}.";
            type uint32;
          }
          container Stats {
            description
            "The CPE MUST reset the Access Point's Stats
            parameters (unless otherwise stated in individual
            object or parameter descriptions) either when the
            Access Point becomes operationally down due to a
            previous administrative down (i.e.  the Access
            Point's Status parameter transitions to a Diasbled
            state) or when the Access Point becomes
            administratively up (i.e.  the Access Point's
            Enable parameter transitions from false to true).
            Administrative and operational status is discussed
            in [Section 4.2.2/TR-181i2].";
            leaf BytesSent {
              config false;
              description
              "The total number of {{units}} transmitted in this
              access category, including framing characters.";
              type yang:counter32;
            }
            leaf BytesReceived {
              config false;
              description
              "The total number of {{units}} received in this
              access category, including framing characters.";
              type yang:counter32;
            }
            leaf PacketsSent {
              config false;
              description
              "The total number of {{units}} transmitted in this
              access category.";
              type yang:counter32;
            }
            leaf PacketsReceived {
              config false;
              description
              "The total number of {{units}} received in this
              access category.";
              type yang:counter32;
            }
            leaf ErrorsSent {
              config false;
              description
              "The total number of outbound {{units}} in this
              access category that could not be transmitted
              because of errors.  These might be due to the
              number of retransmissions exceeding the retry
              limit, or from other causes.";
              type yang:counter32;
            }
            leaf ErrorsReceived {
              config false;
              description
              "The total number of inbound {{units}} in this
              access category that contained errors preventing
              them from being delivered to a higher-layer
              protocol.";
              type yang:counter32;
            }
            leaf DiscardPacketsSent {
              config false;
              description
              "The total number of outbound {{units}} in this
              access category which were chosen to be discarded
              even though no errors had been detected to
              prevent their being transmitted.  One possible
              reason for discarding such a packet could be to
              free up buffer space.";
              type yang:counter32;
            }
            leaf DiscardPacketsReceived {
              config false;
              description
              "The total number of inbound {{units}} in this
              access category which were chosen to be discarded
              even though no errors had been detected to
              prevent their being delivered.  One possible
              reason for discarding such a packet could be to
              free up buffer space.";
              type yang:counter32;
            }
            leaf RetransCount {
              config false;
              description
              "The total number of transmitted {{units}} in this
              access category which were retransmissions.  Two
              retransmissions of the same packet results in
              this counter incrementing by two.";
              type yang:counter32;
            }
            leaf-list OutQLenHistogram {
              config false;
              description
              "{{list}} Histogram of the total length of the
              transmit queue of this access category in packets
              (1 packet, 2 packets, etc.) according to the
              intervals defined by
              {{param|#.OutQLenHistogramIntervals}}, with
              samples taken each
              {{param|#.OutQLenHistogramSampleInterval}}.
              Example: \"12,5,1,0,2,0,0,1\".";
              type string;
            }
          }
        }
        container Accounting {
          description
          "This object contains the parameters related to RADIUS
          accounting functionality for the access point.";
          leaf Enable {
            config true;
            description
            "Enables or disables accounting functionality for
            the access point.";
            type boolean;
          }
          leaf ServerIPAddr {
            config true;
            description
            "The IP Address of the RADIUS accounting server.";
            type inet:ip-address;
          }
          leaf SecondaryServerIPAddr {
            config true;
            description
            "The client can forward requests to the secondary
            server in the event that the primary server is down
            or unreachable, or after a number of tries to the
            primary server fail, or in a round-robin fashion.
            {{bibref|RFC2866}}";
            type inet:ip-address;
          }
          leaf ServerPort {
            config true;
            description
            "The port number of the RADIUS server used for
            accounting.  The default port is 1813 as defined in
            {{bibref|RFC2866}}.";
            type uint32;
            default "1813";
          }
          leaf SecondaryServerPort {
            config true;
            description
            "If this parameter is not implemented, the secondary
            RADIUS server will use the same port number as the
            primary RADIUS server.";
            type uint32;
            default "1813";
          }
          leaf Secret {
            config true;
            description
            "The secret used for handshaking with the RADIUS
            accounting server {{bibref|RFC2865}}.";
            type string;
          }
          leaf SecondarySecret {
            config true;
            description
            "If this parameter is not implemented, the secondary
            RADIUS server will use the same secret as the
            primary RADIUS server.";
            type string;
          }
          leaf InterimInterval {
            config true;
            description
            "A value of 0 means no interim accounting messages
            are sent.";
            type uint32 {
              range "0|60..max";
            }
            default "0";
          }
        }
      }
      list EndPoint {
        key "SSIDReference";
        unique "Alias";
        config true;
        description
        "Note: The {{object}} table includes a unique key
        parameter that is a strong reference.  If a strongly
        referenced object is deleted, the CPE will set the
        referencing parameter to {{empty}}. However, doing so
        under these circumstances might cause the updated
        {{object}} row to then violate the table's unique key
        constraint; if this occurs, the CPE MUST set
        {{param|Status}} to {{enum|Error_Misconfigured|Status}}
        and disable the offending {{object}} row.";
        leaf Enable {
          config true;
          description
          "Enables or disables this end point.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Alias {
          config true;
          description
          "{{datatype|expand}}";
          type Alias;
        }
        leaf ProfileReference {
          config true;
          description
          "{{reference}} This is the currently active profile,
          which specifies the SSID and security settings to be
          used by the end point.";
          type string {
            length "0..256";
          }
        }
        leaf SSIDReference {
          config true;
          description
          "{{reference}} {{param}} is determined based on the
          {{param|Profile.{i}.SSID}} within the associated
          {{param|ProfileReference}}) endpoint profile.
          {{param}} MUST be {{empty}} if
          {{param|ProfileReference}} is {{empty}} (i.e.  only
          when an active profile is assigned can the associated
          SSID interface be determined).";
          type string {
            length "0..256";
          }
        }
        leaf ProfileNumberOfEntries {
          config false;
          description
          "{{numentries}}";
          type uint32;
        }
        container Stats {
          description
          "Throughput statistics for this end point.";
          leaf LastDataDownlinkRate {
            config false;
            description
            "The data transmit rate in {{units}} that was most
            recently used for transmission from the access
            point to the end point device.";
            type uint32 {
              range "1000..600000";
            }
          }
          leaf LastDataUplinkRate {
            config false;
            description
            "The data transmit rate in {{units}} that was most
            recently used for transmission from the end point
            to the access point device.";
            type uint32 {
              range "1000..600000";
            }
          }
          leaf SignalStrength {
            config false;
            description
            "An indicator of radio signal strength of the
            downlink from the access point to the end point,
            measured in {{units}}, as an average of the last
            100 packets received from the device.";
            type int32 {
              range "-200..0";
            }
          }
          leaf Retransmissions {
            config false;
            description
            "The number of {{units}} that had to be
            re-transmitted, from the last 100 packets sent to
            the access point.  Multiple re-transmissions of the
            same packet count as one.";
            type uint32 {
              range "0..100";
            }
            default "0";
          }
        }
        container Security {
          description
          "This object contains security related parameters that
          apply to a WiFi end point {{bibref|802.11-2007}}.";
          leaf-list ModesSupported {
            config false;
            description
            "{{list}} Indicates which security modes this
            {{object|#}} instance is capable of supporting.";
            type enumeration {
              enum "None";
              enum "WEP-64";
              enum "WEP-128";
              enum "WPA-Personal";
              enum "WPA2-Personal";
              enum "WPA-WPA2-Personal";
              enum "WPA-Enterprise";
              enum "WPA2-Enterprise";
              enum "WPA-WPA2-Enterprise";
            }
          }
        }
        list Profile {
          key "SSID Location Priority";
          unique "Alias";
          config true;
          description
          "EndPoint Profile table.";
          leaf Enable {
            config true;
            description
            "When there are multiple WiFi EndPoint Profiles,
            e.g.  each instance supports a different SSID
            and/or different security configuration, this
            parameter can be used to control which of the
            instances are currently enabled.";
            type boolean;
            default "false";
          }
          leaf Status {
            config false;
            description
            "The {{enum|Active}} value is reserved for the
            instance that is actively connected.  The
            {{enum|Available}} value represents an instance
            that is not currently active, but is also not
            disabled or in error.  The {{enum|Error}} value MAY
            be used by the CPE to indicate a locally defined
            error condition.";
            type enumeration {
              enum "Active";
              enum "Available";
              enum "Error";
              enum "Disabled";
            }
            default "Disabled";
          }
          leaf Alias {
            config true;
            description
            "{{datatype|expand}}";
            type Alias;
          }
          leaf SSID {
            config true;
            description
            "The profile identifier in use by the connection.
            The SSID is an identifier that is attached to
            packets sent over the wireless LAN that functions
            as an ID for joining a particular radio network
            (BSS).";
            type string {
              length "0..32";
            }
          }
          leaf Location {
            config true;
            description
            "Location of the profile.  This value serves as a
            reminder from the user, describing the location of
            the profile.  For example: \"Home\", \"Office\",
            \"Neighbor House\", \"Airport\", etc.  An empty
            string is also valid.";
            type string;
          }
          leaf Priority {
            config true;
            description
            "0 is the highest priority.";
            type uint32 {
              range "min..255";
            }
          }
          container Security {
            description
            "This object contains security related parameters
            that apply to a WiFi End Point profile
            {{bibref|802.11-2007}}.";
            leaf ModeEnabled {
              config true;
              description
              "Indicates which security mode is enabled.";
              type string;
              must ". = ../../../Security/ModesSupported";
            }
            leaf WEPKey {
              config true;
              description
              "A 5 byte {{param}} corresponds to security mode
              {{enum|WEP-64|ModeEnabled}} and a 13 byte
              {{param}} corresponds to security mode
              {{enum|WEP-128|ModeEnabled}}.";
              type yang:hex-string {
                length "5|13";
              }
            }
            leaf PreSharedKey {
              config true;
              description
              "If {{param|KeyPassphrase}} is written, then
              {{param}} is immediately generated.  The ACS
              SHOULD NOT set both the {{param|KeyPassphrase}}
              and the {{param}} directly (the result of doing
              this is undefined).";
              type yang:hex-string {
                length "0..32";
              }
            }
            leaf KeyPassphrase {
              config true;
              description
              "If {{param}} is written, then
              {{param|PreSharedKey}} is immediately generated.
              The ACS SHOULD NOT set both the {{param}} and the
              {{param|PreSharedKey}} directly (the result of
              doing this is undefined). The key is generated as
              specified by WPA, which uses PBKDF2 from PKCS #5:
              Password-based Cryptography Specification Version
              2.0 {{bibref|RFC2898}}.";
              type string {
                length "8..63";
              }
            }
            leaf MFPConfig {
              config true;
              description
              "Management Frame Protection configuration
              applicable when {{param|ModeEnabled}} is set to
              {{enum|WPA2-Personal|ModeEnabled}} or
              {{enum|WPA2-Enterprise|ModeEnabled}}.";
              type enumeration {
                enum "Disabled";
                enum "Optional";
                enum "Required";
              }
              default "Disabled";
            }
          }
        }
        container WPS {
          description
          "This object contains parameters related to Wi-Fi
          Protected Setup {{bibref|WPSv1.0}} for this end
          point.";
          leaf Enable {
            config true;
            description
            "Enables or disables WPS functionality for this end
            point.";
            type boolean;
            default "true";
          }
          leaf-list ConfigMethodsSupported {
            config false;
            description
            "The {{enum|USBFlashDrive}} and {{enum|Ethernet}}
            are only applicable in WPS 1.0 and are deprecated
            in WPS 2.x.  The {{enum|PhysicalPushButton}},
            {{enum|VirtualPushButton}},
            {{enum|PhysicalDisplay}} and
            {{enum|VirtualDisplay}} are applicable to WPS 2.x
            only.";
            type enumeration {
              enum "USBFlashDrive";
              enum "Ethernet";
              enum "Label";
              enum "Display";
              enum "ExternalNFCToken";
              enum "IntegratedNFCToken";
              enum "NFCInterface";
              enum "PushButton";
              enum "PIN";
              enum "PhysicalPushButton";
              enum "PhysicalDisplay";
              enum "VirtualPushButton";
              enum "VirtualDisplay";
            }
          }
          leaf-list ConfigMethodsEnabled {
            config true;
            description
            "{{list}} Indicates the WPS configuration methods
            enabled on the device.";
            type string;
            must ". = ../ConfigMethodsSupported";
          }
          leaf Status {
            config false;
            description
            "{{list}} Indicates the current status of WPS in
            EndPoint.";
            type enumeration {
              enum "Disabled";
              enum "Error";
              enum "Unconfigured";
              enum "Configured";
            }
          }
          leaf Version {
            config false;
            description
            "For example, a value of ''1.0'' denotes WSC 1.0 and
            a value of ''2.0'' denotes WSC 2.0.";
            type string;
          }
          leaf PIN {
            config true;
            description
            "{{hidden}}";
            type uint32 {
              range "4|8";
            }
          }
        }
        list AC {
          key "AccessCategory";
          config true;
          description
          "* VO (Voice)";
          leaf AccessCategory {
            config true;
            description
            "This identifies the access category.";
            type enumeration {
              enum "BE";
              enum "BK";
              enum "VI";
              enum "VO";
            }
          }
          leaf Alias {
            config true;
            description
            "{{datatype|expand}}";
            type Alias;
          }
          leaf AIFSN {
            config true;
            description
            "Arbitration Inter Frame Spacing (Number). This is
            the number of time slots in the arbitration
            interframe space.";
            type uint32 {
              range "2..15";
            }
          }
          leaf ECWMin {
            config true;
            description
            "Exponent of Contention Window (Minimum). This
            encodes the values of CWMin as an exponent: CWMin =
            2^ECWMin - 1. For example, if ECWMin is 8, then
            CWMin is 2^8 - 1, or 255, (expressed in {{units}}).";
            type uint32 {
              range "0..15";
            }
          }
          leaf ECWMax {
            config true;
            description
            "Exponent of Contention Window (Maximum). This
            encodes the values of CWMax as an exponent: CWMax =
            2^ECWMax - 1. For example, if ECWMax is 8, then
            CWMax is 2^8 - 1, or 255, (expressed in {{units}}).";
            type uint32 {
              range "0..15";
            }
          }
          leaf TxOpMax {
            config true;
            description
            "Maximum transmit opportunity, in multiples of
            {{units}}. A TXOP time interval of 0 means it is
            limited to a single MAC protocol data unit (MPDU).";
            type uint32 {
              range "0..255";
            }
          }
          leaf AckPolicy {
            config true;
            description
            "Ack Policy, where False=\"Do Not Acknowledge\" and
            True=\"Acknowledge\"";
            type boolean;
          }
          leaf-list OutQLenHistogramIntervals {
            config true;
            description
            "{{list}} Definition of the histogram intervals for
            counting the transmit queue length in packets.
            Each value indicates the maximum value of the
            interval.  For example, \"0,1,4,8,\" defines the
            five intervals: 0 packets in queue, 1 packet in
            queue, 2 to 4 packets in queue, 5 to 8 packets in
            queue, and 9 or more packets in queue.  (No value
            after the last comma means no upper bound.) If this
            parameter is set to an empty string, no
            {{param|Stats.OutQLenHistogram}} stats will be
            collected.";
            type string;
          }
          leaf OutQLenHistogramSampleInterval {
            config true;
            description
            "The time between recording samples of the current
            transmit queue {{units}}.";
            type uint32;
          }
          container Stats {
            description
            "The CPE MUST reset the EndPoint's Stats parameters
            (unless otherwise stated in individual object or
            parameter descriptions) either when the EndPoint
            becomes operationally down due to a previous
            administrative down (i.e.  the EndPoint's Status
            parameter transitions to a Diasbled state) or when
            the EndPoint becomes administratively up (i.e.  the
            EndPoint's Enable parameter transitions from false
            to true). Administrative and operational status is
            discussed in [Section 4.2.2/TR-181i2].";
            leaf BytesSent {
              config false;
              description
              "The total number of {{units}} transmitted in this
              access category, including framing characters.";
              type yang:counter32;
            }
            leaf BytesReceived {
              config false;
              description
              "The total number of {{units}} received in this
              access category, including framing characters.";
              type yang:counter32;
            }
            leaf PacketsSent {
              config false;
              description
              "The total number of {{units}} transmitted in this
              access category.";
              type yang:counter32;
            }
            leaf PacketsReceived {
              config false;
              description
              "The total number of {{units}} received in this
              access category.";
              type yang:counter32;
            }
            leaf ErrorsSent {
              config false;
              description
              "The total number of outbound {{units}} in this
              access category that could not be transmitted
              because of errors.  These might be due to the
              number of retransmissions exceeding the retry
              limit, or from other causes.";
              type yang:counter32;
            }
            leaf ErrorsReceived {
              config false;
              description
              "The total number of inbound {{units}} in this
              access category that contained errors preventing
              them from being delivered to a higher-layer
              protocol.";
              type yang:counter32;
            }
            leaf DiscardPacketsSent {
              config false;
              description
              "The total number of outbound {{units}} in this
              access category which were chosen to be discarded
              even though no errors had been detected to
              prevent their being transmitted.  One possible
              reason for discarding such a packet could be to
              free up buffer space.";
              type yang:counter32;
            }
            leaf DiscardPacketsReceived {
              config false;
              description
              "The total number of inbound {{units}} in this
              access category which were chosen to be discarded
              even though no errors had been detected to
              prevent their being delivered.  One possible
              reason for discarding such a packet could be to
              free up buffer space.";
              type yang:counter32;
            }
            leaf RetransCount {
              config false;
              description
              "The total number of transmitted {{units}} in this
              access category which were retransmissions.  Two
              retransmissions of the same packet results in
              this counter incrementing by two.";
              type yang:counter32;
            }
            leaf-list OutQLenHistogram {
              config false;
              description
              "{{list}} Histogram of the total length of the
              transmit queue of this access category in packets
              (1 packet, 2 packets, etc.) according to the
              intervals defined by
              {{param|#.OutQLenHistogramIntervals}}, with
              samples taken each
              {{param|#.OutQLenHistogramSampleInterval}}.
              Example: \"12,5,1,0,2,0,0,1\"";
              type string;
            }
          }
        }
      }
    }
    container ZigBee {
      description
      "Top level object for ZigBee capabilities based on the
      {{bibref|ZigBee2007}} specification.";
      leaf InterfaceNumberOfEntries {
        config false;
        description
        "{{numentries}}";
        type uint32;
      }
      leaf ZDONumberOfEntries {
        config false;
        description
        "{{numentries}}";
        type uint32;
      }
      list Interface {
        key "ZDOReference";
        unique "Alias";
        unique "Name";
        config true;
        description
        "ZigBee interface table (a stackable interface object as
        described in {{bibref|TR-181i2|Section 4.2}}). This
        table models the ZigBee interface of a ZigBee end
        device, ZigBee router or ZigBee coordinator.";
        leaf Enable {
          config true;
          description
          "Enables or disables the interface.  This parameter is
          based on ''ifAdminStatus'' from {{bibref|RFC2863}}.";
          type boolean;
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
        }
        leaf Alias {
          config true;
          description
          "{{datatype|expand}}";
          type Alias;
        }
        leaf Name {
          config false;
          description
          "The textual name of the interface as assigned by the
          CPE.";
          type string {
            length "0..64";
          }
        }
        leaf LastChange {
          config false;
          description
          "The accumulated time in {{units}} since the interface
          entered its current operational state.";
          type uint32;
        }
        leaf-list LowerLayers {
          config true;
          description
          "{{list}} {{reference|an interface object that is
          stacked immediately below this interface object}}
          See {{bibref|TR-181i2|Section 4.2.1}}.";
          type string;
        }
        leaf IEEEAddress {
          config false;
          description
          "The IEEE address assigned to this interface.  A value
          of \"FF:FF:FF:FF:FF:FF:FF:FF\"  indicates that this
          address is unknown.  This parameter has the same
          value as the {{param|.ZigBee.ZDO.{i}.IEEEAddress}}
          parameter of the ZDO instance {{param|ZDOReference}}
          is pointing to.";
          type IEEE_EUI64;
        }
        leaf NetworkAddress {
          config false;
          description
          "The ZigBee network address assigned to this
          interface.  This parameter has the same value as the
          {{param|.ZigBee.ZDO.{i}.NetworkAddress}} parameter of
          the ZDO instance {{param|ZDOReference}} is pointing
          to.";
          type ZigBeeNetworkAddress;
        }
        leaf ZDOReference {
          config true;
          description
          "The ZigBee Device Object assigned to this interface.";
          type string {
            length "0..256";
          }
        }
        leaf AssociatedDeviceNumberOfEntries {
          config false;
          description
          "{{numentries}}";
          type uint32;
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of {{units}} transmitted out of
            the interface, including framing characters.";
            type yang:counter32;
          }
          leaf BytesReceived {
            config false;
            description
            "The total number of {{units}}  received on the
            interface, including framing characters.";
            type yang:counter32;
          }
          leaf PacketsSent {
            config false;
            description
            "The total number of {{units}} sent transmitted out
            of the interface.";
            type yang:counter32;
          }
          leaf PacketsReceived {
            config false;
            description
            "The total number of {{units}} received by the
            interface.";
            type yang:counter32;
          }
          leaf ErrorsSent {
            config false;
            description
            "The total number of {{units}} discarded by
            interface due to any error.";
            type yang:counter32;
          }
          leaf ErrorsReceived {
            config false;
            description
            "The total number of {{units}} received that
            contained errors preventing them from being
            delivered to a higher-layer protocol.";
            type yang:counter32;
          }
          leaf UnicastPacketsSent {
            config false;
            description
            "The total number of {{units}} requested for
            transmission which were not addressed to a
            multicast or broadcast address at this layer,
            including those that were discarded or not sent.";
            type yang:counter32;
          }
          leaf UnicastPacketsReceived {
            config false;
            description
            "The total number of {{units}} received which were
            not addressed to a multicast or broadcast address
            at this layer.";
            type yang:counter32;
          }
          leaf DiscardPacketsSent {
            config false;
            description
            "The total number of {{units}} requested for
            transmission which were chosen to be discarded even
            though no errors had been detected to prevent the
            {{units}} being transmitted.";
            type yang:counter32;
          }
          leaf DiscardPacketsReceived {
            config false;
            description
            "The total number of {{units}} received which were
            chosen to be discarded even though no errors had
            been detected to prevent their being delivered.";
            type yang:counter32;
          }
          leaf MulticastPacketsSent {
            config false;
            description
            "The total number of {{units}} requested for
            transmission which were addressed to a multicast
            address at this layer, including those that were
            discarded or not sent.";
            type yang:counter32;
          }
          leaf MulticastPacketsReceived {
            config false;
            description
            "The total number of {{units}} received which were
            addressed to a multicast address at this layer and
            delivered by this layer to a higher layer.";
            type yang:counter32;
          }
          leaf BroadcastPacketsSent {
            config false;
            description
            "The total number of {{units}} requested for
            transmission which were addressed to a broadcast
            address at this layer, including those that were
            discarded or not sent.";
            type yang:counter32;
          }
          leaf BroadcastPacketsReceived {
            config false;
            description
            "The total number of {{units}} received which were
            addressed to a broadcast address at this layer and
            delivered by this layer to a higher layer.";
            type yang:counter32;
          }
          leaf UnknownPacketsReceived {
            config false;
            description
            "The total number of {{units}} received which were
            discarded because of an unknown or unsupported
            protocol.";
            type yang:counter32;
          }
        }
        list AssociatedDevice {
          key "IEEEAddress NetworkAddress";
          config false;
          description
          "It is possible that instances of this object have the
          same key value when the value of
          {{param|IEEEAddress}} parameter is
          \"FF:FF:FF:FF:FF:FF:FF:FF\" and the ZigBee
          Coordinators on two or more separate area networks
          assign the same value for the
          {{param|NetworkAddress}}. This is because the ZigBee
          specification describes only intra-area network
          topologies {{bibref|ZigBee2007|Section 1.1.4 Network
          Topology}}. As such if two or more {{object}}
          instances have the same key value the implemenation
          is undefined.";
          leaf IEEEAddress {
            config false;
            description
            "The IEEE address assigned to this device.  A value
            of \"FF:FF:FF:FF:FF:FF:FF:FF\"  indicates that this
            address is unknown.";
            type IEEE_EUI64;
          }
          leaf NetworkAddress {
            config false;
            description
            "The ZigBee network address assigned to this device.";
            type ZigBeeNetworkAddress;
          }
          leaf Active {
            config false;
            description
            "The ability to list inactive devices is OPTIONAL.
            If the CPE includes inactive devices in this table,
            {{param}} MUST be set to {{false}}  for each
            inactive device.  The length of time an inactive
            device remains listed in this table is a local
            matter to the CPE.";
            type boolean;
          }
          leaf ZDOReference {
            config false;
            description
            "The ZigBee Device Object assigned to this
            interface.";
            type string {
              length "0..256";
            }
          }
        }
      }
      list ZDO {
        key "IEEEAddress NetworkAddress";
        config true;
        description
        "It is possible that instances of this object have the
        same key value when the value of {{param|IEEEAddress}}
        parameter is \"FF:FF:FF:FF:FF:FF:FF:FF\" and the ZigBee
        Coordinators on two or more separate area networks
        assign the same value for the {{param|NetworkAddress}}.
        This is because the ZigBee specification describes only
        intra-area network topologies
        {{bibref|ZigBee2007|Section 1.1.4 Network Topology}}.
        As such if two or more {{object}} instances have the
        same key value the implemenation is undefined";
        leaf Alias {
          config true;
          description
          "{{datatype|expand}}";
          type Alias;
        }
        leaf IEEEAddress {
          config true;
          description
          "The IEEE address assigned to this device.  A value of
          \"FF:FF:FF:FF:FF:FF:FF:FF\"  indicates that this
          address is unknown.";
          type IEEE_EUI64;
        }
        leaf NetworkAddress {
          config true;
          description
          "The ZigBee network address assigned to this device.";
          type ZigBeeNetworkAddress;
        }
        leaf BindingTableNumberOfEntries {
          config false;
          description
          "{{numentries}}";
          type uint32;
        }
        leaf GroupNumberOfEntries {
          config false;
          description
          "{{numentries}}";
          type uint32;
        }
        leaf ApplicationEndpointNumberOfEntries {
          config false;
          description
          "{{numentries}}";
          type uint32;
        }
        container NodeDescriptor {
          description
          "The {{object}} object describes the node capabilities
          of the ZigBee device as defined in
          {{bibref|ZigBee2007|section 2.3.2.3 Node
          Descriptor}}.";
          leaf LogicalType {
            config false;
            description
            "{{enum}}";
            type enumeration {
              enum "ZC" {
                description
                "ZigBee Coordinator";
              }
              enum "ZR" {
                description
                "ZigBee Router";
              }
              enum "ZED" {
                description
                "ZigBee End Device";
              }
            }
          }
          leaf ComplexDescriptorSupported {
            config false;
            description
            "When {{true}}, specifies that the
            {{object|#.ComplexDescriptor}} object is supported
            for this ZigBee device.";
            type boolean;
          }
          leaf UserDescriptorSupported {
            config false;
            description
            "When {{true}}, specifies that the
            {{object|#.UserDescriptor}} object is supported for
            this ZigBee device.";
            type boolean;
          }
          leaf-list FrequencyBand {
            config false;
            description
            "{{list}} {{enum}}";
            type enumeration {
              enum "868-868.6" {
                description
                "The 868-868.6 MHz Band";
              }
              enum "902-928" {
                description
                "The 902-928 MHz Band";
              }
              enum "2400-2483.5" {
                description
                "The 2400-2483.5 MHz Band";
              }
            }
          }
          leaf-list MACCapability {
            config false;
            description
            "{{list}} {{enum}}";
            type enumeration {
              enum "AlternatePANCoordinator" {
                description
                "Alternate PAN Coordinator";
              }
              enum "FFD" {
                description
                "Full Function Device";
              }
              enum "MainsPowerSource" {
                description
                "The current power source is mains power";
              }
              enum "OnWhenIdle" {
                description
                "The receiver is on when idle";
              }
              enum "SecureCommunication" {
                description
                "Secure communication is enabled";
              }
            }
          }
          leaf ManufactureCode {
            config false;
            description
            "Specifies a manufacturer code that is allocated by
            the ZigBee Alliance, relating the manufacturer to
            the device.";
            type uint32 {
              range "min..65535";
            }
          }
          leaf MaximumBufferSize {
            config false;
            description
            "Specifies the maximum buffer size, in {{units}}, of
            the network sub-layer data unit (NSDU) for this
            ZigBee device.";
            type uint32 {
              range "min..128";
            }
          }
          leaf MaximumIncomingTransferSize {
            config false;
            description
            "Specifies the maximum size, in {{units}}, of the
            application sub-layer data unit (ASDU) that can be
            transferred to this ZigBee device in one single
            message transfer.";
            type uint32 {
              range "min..32768";
            }
          }
          leaf MaximumOutgoingTransferSize {
            config false;
            description
            "Specifies the maximum size, in {{units}}, of the
            application sub-layer data unit (ASDU) that can be
            transferred from this ZigBee device in one single
            message transfer.";
            type uint32 {
              range "min..32768";
            }
          }
          leaf-list ServerMask {
            config false;
            description
            "{{list}} {{enum}}";
            type enumeration {
              enum "PrimaryTrustCenter";
              enum "PrimaryBindingTableCache";
              enum "BackupBindingTableCache";
              enum "PrimaryDiscoveryCache";
              enum "BackupDiscoveryCache";
              enum "NetworkManager";
            }
          }
          leaf-list DescriptorCapability {
            config false;
            description
            "{{list}} {{enum}}";
            type enumeration {
              enum "ExtendedActiveEndpointListAvailable";
              enum "ExtendedSimpleDescriptorListAvailable";
            }
          }
        }
        container PowerDescriptor {
          description
          "The {{object}} object describes the power
          capabilities of the ZigBee device as defined in
          {{bibref|ZigBee2007|section 2.3.2.4 Node Power
          Descriptor}}.";
          leaf CurrentPowerMode {
            config false;
            description
            "{{enum}}";
            type enumeration {
              enum "Synchronized";
              enum "Periodic";
              enum "Manual";
            }
          }
          leaf-list AvailablePowerSource {
            config false;
            description
            "{{list}} {{enum}}";
            type enumeration {
              enum "Constant" {
                description
                "Constant (mains) power";
              }
              enum "Rechargeable" {
                description
                "Rechargable battery";
              }
              enum "Disposable" {
                description
                "Disposable battery";
              }
            }
          }
          leaf CurrentPowerSource {
            config false;
            description
            "{{enum}}";
            type enumeration {
              enum "Constant" {
                description
                "Constant (mains) power";
              }
              enum "Rechargeable" {
                description
                "Rechargable battery";
              }
              enum "Disposable" {
                description
                "Disposable battery";
              }
            }
          }
          leaf CurrentPowerSourceLevel {
            config false;
            description
            "{{enum}}";
            type enumeration {
              enum "Critical" {
                description
                "Critical battery state";
              }
              enum "33" {
                description
                "Battery state is 33 percent";
              }
              enum "66" {
                description
                "Battery state is 66 percent";
              }
              enum "100" {
                description
                "Battery state is 100 percent";
              }
            }
          }
        }
        container UserDescriptor {
          description
          "The {{object}} object is an optional descriptor that
          describes user defined capabilities of the ZigBee
          device as defined in {{bibref|ZigBee2007|section
          2.3.2.7 User Descriptor}}. The {{object}} object
          contains information that allows the user to identify
          the device using a user-friendly character string,
          such as \"Bedroom TV\" or \"Stairs Light\".";
          leaf DescriptorAvailable {
            config false;
            description
            "When {{true}}, the User Descriptor recorded has
            been received from the target device.";
            type boolean;
          }
          leaf Description {
            config false;
            description
            "Specifies the information that allows the user to
            identify the ZigBee device using a user-friendly
            character string, such as \"Bedroom TV\" or
            \"Stairs light\".";
            type string {
              length "0..16";
            }
          }
        }
        container ComplexDescriptor {
          description
          "The {{object}} object is an optional descriptor that
          describes extended capabilities of the ZigBee device
          as defined in {{bibref|ZigBee2007|section 2.3.2.6
          Complex Descriptor}}.";
          leaf DescriptorAvailable {
            config false;
            description
            "When {{true}}, the Complex Descriptor recorded has
            been received from the target device.";
            type boolean;
          }
          leaf Language {
            config false;
            description
            "Specifies the ISO 639-1 language code as defined in
            {{bibref|ISO639-1}}.";
            type string;
          }
          leaf CharacterSet {
            config false;
            description
            "Specifies the ISO 646 character set as defined in
            {{bibref|ISO646-1991}}.";
            type string;
          }
          leaf ManufacturerName {
            config false;
            description
            "Specifies the name of the manufacturer of the
            ZigBee device.";
            type string;
          }
          leaf ModelName {
            config false;
            description
            "Specifies the name of the manufacturer's model of
            the ZigBee device.";
            type string;
          }
          leaf SerialNumber {
            config false;
            description
            "Specifies the manufacturer's serial number of the
            ZigBee device.";
            type string;
          }
          leaf DeviceURL {
            config false;
            description
            "Specifies the URL through which more information
            relating to the ZigBee device can be obtained.";
            type string;
          }
          leaf Icon {
            config false;
            description
            "The icon field contains an octet string which
            carries the data for an icon that can represent the
            ZigBee device.  The format of the icon MUST be a
            32-by-32-pixel PNG image.";
            type yang:hex-string {
              length "0..65535";
            }
          }
          leaf IconURL {
            config false;
            description
            "Specifies the URL through which the icon for the
            ZigBee device can be obtained.";
            type string;
          }
        }
        container Security {
          description
          "The {{object}} object provides the configuration
          capabilities needed to perform the Security
          Management functionality defined in
          {{bibref|ZigBee2007|section 4 Security Management}}.";
          leaf TrustCenterAddress {
            config false;
            description
            "Specifies the IEEE address of a special device
            trusted by devices within a ZigBee network to
            distribute keys for the purpose of network and
            end-to-end application configuration management.";
            type IEEE_EUI64;
          }
          leaf SecurityLevel {
            config false;
            description
            "{{enum}}";
            type enumeration {
              enum "None";
              enum "MIC-32";
              enum "MIC-64";
              enum "MIC-128";
              enum "ENC";
              enum "ENC-MIC-32";
              enum "ENC-MIC-64";
              enum "ENC-MIC-128";
            }
          }
          leaf TimeOutPeriod {
            config false;
            description
            "The period of time, in {{units}}, that this ZigBee
            device will wait for an expected security protocol
            frame.";
            type uint32 {
              range "min..65535";
            }
          }
        }
        container Network {
          description
          "The {{object}} object provides the configuration
          capabilities needed to by a ZigBee Device to operate
          within a ZigBee Area Network as defined in
          {{bibref|ZigBee2007|section 2.5.2.4 Network
          Manager}}.";
          leaf NeighborNumberOfEntries {
            config false;
            description
            "{{numentries}}";
            type uint32;
          }
          list Neighbor {
            key "Neighbor";
            config false;
            description
            "The {{object}} object provides the configuration
            capabilities needed to by a ZigBee Device to
            operate within a ZigBee Area Network as defined in
            {{bibref|ZigBee2007|section 2.5.2.4 Network
            Manager}}.";
            leaf Neighbor {
              config false;
              description
              "Neighbor of this ZigBee device.  The value MUST
              be the path name of a row in the ZigBee.ZDO
              table.  If the referenced row is deleted then
              this entry MUST be deleted.";
              type string;
            }
            leaf LQI {
              config false;
              description
              "The LQI field specified link quality
              identification (LQI) for neighbor ZigBee device.";
              type uint32 {
                range "min..255";
              }
            }
            leaf Relationship {
              config false;
              description
              "The relationship between the neighbor and this
              device.{{enum}}";
              type enumeration {
                enum "Parent";
                enum "Child";
                enum "PrevChild";
                enum "Sibling";
                enum "None";
              }
            }
            leaf PermitJoin {
              config false;
              description
              "An indication of whether the neighbor device is
              accepting join requests.{{enum}}";
              type enumeration {
                enum "Accepting";
                enum "NotAccepting";
                enum "Unknown";
              }
            }
            leaf Depth {
              config false;
              description
              "The tree depth of the neighbor device.  A value
              of 0x00 indicates that the device is the ZigBee
              coordinator for the network.";
              type uint32;
            }
          }
        }
        container NodeManager {
          description
          "The {{object}} object describes the configuration
          capabilities related for remote management of the
          ZigBee Area Network as defined in
          {{bibref|ZigBee2007|section 2.5.2.6 Node Manager}}.";
          leaf RoutingTableNumberOfEntries {
            config false;
            description
            "{{numentries}}";
            type uint32;
          }
          list RoutingTable {
            key "DestinationAddress";
            config false;
            description
            "The {{object}} object describes the route table as
            defined in {{bibref|ZigBee2007|table 3.51 Routing
            Table Entry}}.";
            leaf DestinationAddress {
              config false;
              description
              "The ZigBee network address of this route.";
              type string {
                length "0..4";
                pattern "([0-9A-Fa-f]){4}";
              }
            }
            leaf NextHopAddress {
              config false;
              description
              "Specifies the network address of the next hop
              ZigBee device on the way to the destination
              ZigBee device.";
              type ZigBeeNetworkAddress;
            }
            leaf Status {
              config false;
              description
              "The status of the route entry.  {{enum}}";
              type enumeration {
                enum "Active";
                enum "DiscoveryUnderway";
                enum "DiscoveryFailed";
                enum "Inactive";
                enum "ValidationUnderway";
              }
            }
            leaf MemoryConstrained {
              config false;
              description
              "A flag indicating whether the device is a memory
              constrained concentrator.";
              type boolean;
            }
            leaf ManyToOne {
              config false;
              description
              "A flag indicating that the destination is a
              concentrator that issued a many to-one request.";
              type boolean;
            }
            leaf RouteRecordRequired {
              config false;
              description
              "A flag indicating that a route record command
              frame should be sent to the destination prior to
              the next data packet.";
              type boolean;
            }
          }
        }
        list Binding {
          key "Alias";
          config true;
          description
          "The {{object}} object describes the configuration
          capabilities related to maintaining a ZigBee Device's
          Binding Table as defined in
          {{bibref|ZigBee2007|section 2.2.8.2 Binding}}.";
          leaf Enable {
            config true;
            description
            "Enables or disables the use of this binding on the
            device.";
            type boolean;
          }
          leaf Alias {
            config true;
            description
            "{{datatype|expand}}";
            type Alias;
          }
          leaf SourceEndpoint {
            config true;
            description
            "Specifies the source endpoint used in this binding
            entry.";
            type uint32 {
              range "min..240";
            }
          }
          leaf SourceAddress {
            config true;
            description
            "Specifies the source address used in this binding
            entry.";
            type IEEE_EUI64;
          }
          leaf ClusterId {
            config true;
            description
            "Specifies the cluster identifier used in this
            binding entry.";
            type uint32 {
              range "min..65535";
            }
          }
          leaf DestinationAddressMode {
            config true;
            description
            "Specifies the type of destination address used for
            this binding entry.  {{enum}}";
            type enumeration {
              enum "Group";
              enum "Endpoint";
            }
          }
          leaf DestinationEndpoint {
            config true;
            description
            "Specifies the destination endpoint for the binding
            entry.  The value of this field is valid when the
            value of the {{param|DestinationAddressMode}} is
            {{enum|Endpoint|DestinationAddressMode}}.";
            type uint32 {
              range "min..240";
            }
          }
          leaf IEEEDestinationAddress {
            config true;
            description
            "Specifies the IEEE destination address for this
            binding entry.  The value of this field is valid
            when the value of the
            {{param|DestinationAddressMode}} is
            {{enum|Endpoint|DestinationAddressMode}}.";
            type IEEE_EUI64;
          }
          leaf GroupDestinationAddress {
            config true;
            description
            "Specifies the group destination address for this
            binding entry.  The value of this field is valid
            when the value of the
            {{param|DestinationAddressMode}} is
            {{enum|Group|DestinationAddressMode}}.";
            type ZigBeeNetworkAddress;
          }
        }
        list Group {
          key "GroupId";
          unique "Alias";
          config true;
          description
          "The {{object}} object describes the configuration
          capabilities related to maintaining a ZigBee Device's
          Group Table as defined in {{bibref|ZigBee2007|section
          2.5.2.7 Group Manager}}.";
          leaf Enable {
            config true;
            description
            "Enables or disables the use of this group on the
            device.";
            type boolean;
          }
          leaf Alias {
            config true;
            description
            "{{datatype|expand}}";
            type Alias;
          }
          leaf GroupId {
            config true;
            description
            "The Group Identifier for this object as defined in
            {{bibref|ZigBee2007|table 2.25 Group Table Entry
            Format}}.";
            type ZigBeeNetworkAddress;
          }
          leaf-list EndpointList {
            config true;
            description
            "The list of application endpoints assigned as a
            member of this {{object}} object.";
            type string {
              length "0..256";
            }
          }
        }
        list ApplicationEndpoint {
          key "EndpointId";
          unique "Alias";
          config true;
          description
          "The {{object}} object describes the application
          endpoint as defined in {{bibref|ZigBee2007|section
          2.1.2 Application Framework}}.";
          leaf Enable {
            config true;
            description
            "Enables or disables the use of this application
            endpoint on the device.";
            type boolean;
          }
          leaf Alias {
            config true;
            description
            "{{datatype|expand}}";
            type Alias;
          }
          leaf EndpointId {
            config true;
            description
            "An {{object}} with an {{param}} value of 0 is
            designated as the device application: This is a
            special application that is responsible for device
            operation and contains logic to manage the device's
            networking and general maintenance features.";
            type uint32 {
              range "min..240";
            }
          }
          container SimpleDescriptor {
            description
            "The {{object}} object contains the attributes of
            the Simple Descriptor of an application endpoint,
            as defined in {{bibref|ZigBee2007|section 2.3.2.5
            Simple Descriptor}}.";
            leaf ProfileId {
              config true;
              description
              "Specifies the application profile that is
              supported on this endpoint.  Application profiles
              are agreements for messages, message formats,
              andprocessing actions that enable developers to
              create an interoperable, distributed application
              employing application entities that reside on
              separate ZigBee devices.  These application
              profiles enable applications to send commands,
              request data, and process commands and requests
              as defined in {{bibref|ZigBee2007|section 2.1.2.1
              Application Profiles}}.";
              type uint32 {
                range "min..65535";
              }
            }
            leaf DeviceId {
              config false;
              description
              "Application device identifier, as defined in
              {{bibref|ZigBee2007|section 2.3.2.5.3 Application
              Device Identifier Field}}.";
              type uint32 {
                range "min..65535";
              }
            }
            leaf DeviceVersion {
              config false;
              description
              "Application device version, as defined in
              {{bibref|ZigBee2007|section 2.3.2.5.4 Application
              Device Version Field}}.";
              type uint32 {
                range "min..15";
              }
            }
            leaf-list InputClusterList {
              config true;
              description
              "{{list}} Specifies the input cluster identifiers
              to be matched by the ZigBee coordinator by remote
              Zigbee device's output cluster list for this
              {{object}} object.";
              type uint32 {
                range "min..65535";
              }
            }
            leaf-list OutputClusterList {
              config true;
              description
              "{{list}} Specifies the output cluster identifiers
              to be matched by the ZigBee coordinator by remote
              Zigbee device's input cluster list for this
              {{object}} object.";
              type uint32 {
                range "min..65535";
              }
            }
          }
        }
      }
      container Discovery {
        description
        "This object is used for managing the discovery of
        ZigBee devices within a ZigBee Area Network.  ZigBee
        Devices are discovered via the {{object|#.ZDO}}
        instance associated with the ZigBee Coordinator of an
        Area Network.";
        leaf AreaNetworkNumberOfEntries {
          config false;
          description
          "{{numentries}}";
          type uint32;
        }
        list AreaNetwork {
          key "Coordinator";
          unique "Alias";
          config true;
          description
          "As the ZigBee specification does not provide a
          discovery protocol between the CWMP proxy and the
          ZigBee coordinator, the {{object}} object is
          provisioned and not discovered.";
          leaf Enable {
            config true;
            description
            "Enables or disables discovery of the ZigBee devices
            in this {{object}}.";
            type boolean;
          }
          leaf LastUpdate {
            config false;
            description
            "The date and time when this {{object}} or its
            member devices (i.e., the devices with ZDOs listed
            in {{param|ZDOList}}) were updated due to a
            discovery operation.";
            type yang:date-and-time;
          }
          leaf Status {
            config false;
            description
            "{{enum}}";
            type enumeration {
              enum "Indeterminate" {
                description
                "The discovery operation has not been executed
                and there are no valid discovery results
                available)";
              }
              enum "InProgress";
              enum "Success";
              enum "Error";
              enum "Error_Timeout";
            }
          }
          leaf Alias {
            config true;
            description
            "{{datatype|expand}}";
            type Alias;
          }
          leaf Coordinator {
            config true;
            description
            "The Fully Qualified Domain Name (FQDN) or IP
            address of the ZigBee Coordinator.  The coordinator
            MAY be located within the CPE. In this scenario the
            ACS or CPE MAY use the value of \"localhost\".";
            type string {
              length "0..256";
            }
          }
          leaf ZDOReference {
            config false;
            description
            "{{reference}}";
            type string {
              length "0..256";
            }
          }
          leaf-list ZDOList {
            config false;
            description
            "{{reference}}";
            type string {
              length "0..256";
            }
          }
        }
      }
    }
    container Bridging {
      description
      "802.1Q {{bibref|802.1Q-2011}} bridges incorporate 802.1Q
      {{bibref|802.1Q-2005}} customer and 802.1ad
      {{bibref|802.1ad-2005}} provider bridges.";
      leaf MaxBridgeEntries {
        config false;
        description
        "The maximum number of entries available in the
        {{object|.Bridging.Bridge}} table.";
        type uint32;
      }
      leaf MaxDBridgeEntries {
        config false;
        description
        "There is no guarantee that this many 802.1D Bridges can
        be configured.  For example, the CPE might not be able
        simultaneously to  support both 802.1D and 802.1Q
        Bridges.";
        type uint32;
      }
      leaf MaxQBridgeEntries {
        config false;
        description
        "There is no guarantee that this many 802.1Q Bridges can
        be configured.  For example, the CPE might not be able
        simultaneously to support both 802.1D and 802.1Q
        Bridges.";
        type uint32;
      }
      leaf MaxVLANEntries {
        config false;
        description
        "The maximum number of 802.1Q {{bibref|802.1Q-2011}}
        VLANs supported per {{object|.Bridging.Bridge}} table
        entry.";
        type uint32;
      }
      leaf MaxProviderBridgeEntries {
        config false;
        description
        "The maximum number of entries available in the
        {{object|.Bridging.ProviderBridge}} table.  A non-zero
        value for this parameter implies support for 802.1Q
        Provider Bridges.";
        type uint32;
      }
      leaf ProviderBridgeNumberOfEntries {
        config false;
        description
        "{{numentries}}";
        type uint32;
      }
      leaf MaxFilterEntries {
        config false;
        description
        "The maximum number of entries available in the
        {{object|Filter}} table.";
        type uint32;
      }
      leaf BridgeNumberOfEntries {
        config false;
        description
        "{{numentries}}";
        type uint32;
      }
      leaf FilterNumberOfEntries {
        config false;
        description
        "{{numentries}}";
        type uint32;
      }
      list Bridge {
        key "Alias";
        config true;
        description
        "Bridge table.";
        leaf Enable {
          config true;
          description
          "Enables or disables this {{object}}.";
          type boolean;
          default "false";
        }
        leaf Status {
          config false;
          description
          "The {{enum|Error}} value MAY be used by the CPE to
          indicate a locally defined error condition.";
          type enumeration {
            enum "Disabled";
            enum "Enabled";
            enum "Error";
          }
          default "Disabled";
        }
        leaf Alias {
          config true;
          description
          "{{datatype|expand}}";
          type Alias;
        }
        leaf Standard {
          config true;
          description
          "Selects the standard supported by this Bridge table
          entry.";
          type enumeration {
            enum "802.1D-2004" {
              description
              "{{bibref|802.1D-2004}}";
            }
            enum "802.1Q-2005" {
              description
              "{{bibref|802.1Q-2005}}";
            }
            enum "802.1Q-2011" {
              description
              "The {{object}} provides support for at least one
              feature defined in {{bibref|802.1Q-2011}} that
              was not defined in {{bibref|802.1Q-2005}}.";
            }
          }
        }
        leaf PortNumberOfEntries {
          config false;
          description
          "{{numentries}}";
          type uint32;
        }
        leaf VLANNumberOfEntries {
          config false;
          description
          "{{numentries}}";
          type uint32;
        }
        leaf VLANPortNumberOfEntries {
          config false;
          description
          "{{numentries}}";
          type uint32;
        }
        list Port {
          key "Name";
          unique "Alias";
          config true;
          description
          "There are two types of bridge ports: management
          (upward facing) and non-management (downward facing).
          This is determined by configuring the Boolean
          {{param|ManagementPort}} parameter.  The CPE will
          automatically configure each management bridge port
          to appear in the interface stack above all
          non-management bridge ports that share the same
          {{object|##.Bridge}} instance.";
          leaf Enable {
            config true;
            description
            "This parameter is based on ''ifAdminStatus'' from
            {{bibref|RFC2863}}.";
            type boolean;
            default "false";
          }
          leaf Status {
            config false;
            description
            "This parameter is based on ''ifOperStatus'' from
            {{bibref|RFC2863}}.";
            type enumeration {
              enum "Up";
              enum "Down";
              enum "Unknown";
              enum "Dormant";
              enum "NotPresent";
              enum "LowerLayerDown";
              enum "Error";
            }
            default "Down";
          }
          leaf Alias {
            config true;
            description
            "{{datatype|expand}}";
            type Alias;
          }
          leaf Name {
            config true;
            description
            "The textual name of the bridge port as assigned by
            the CPE.";
            type string {
              length "0..64";
            }
          }
          leaf LastChange {
            config false;
            description
            "The accumulated time in {{units}} since the bridge
            port entered its current operational state.";
            type uint32;
          }
          leaf-list LowerLayers {
            config true;
            description
            "When {{param|ManagementPort}} is set to {{true}}
            the CPE MUST set {{param}} to reference all
            non-management bridge ports that are within the
            same {{object|##.Bridge}} instance (and update
            {{param}} when subsequent non-management bridge
            ports are added or deleted on that ''Bridge''). The
            ACS SHOULD NOT set {{param}} in this case.";
            type string;
          }
          leaf ManagementPort {
            config true;
            description
            "If {{true}} then the entry is a management (upward
            facing) bridge port rather than a non-management
            (downward facing) bridge port.  For a given
            {{object|##.Bridge}} instance, each management
            bridge port appears in the interface stack above
            all non-management bridge ports.  The concept of
            Management Port is discussed in
            {{bibref|802.1Q-2005|chapter 8}}.";
            type boolean;
            default "false";
          }
          leaf Type {
            config true;
            description
            "{{enum}}";
            type enumeration {
              enum "ProviderNetworkPort" {
                description
                "Indicates this {{object}} is an S-TAG aware
                port of a {{object|##.ProviderBridge}}.";
              }
              enum "CustomerNetworkPort" {
                description
                "Indicates this {{object}} is an S-TAG aware
                port of a {{object|##.ProviderBridge}}.";
              }
              enum "CustomerEdgePort" {
                description
                "Indicates this {{object}} is an C-TAG aware
                port of a {{object|##.ProviderBridge}}.";
              }
              enum "CustomerVLANPort" {
                description
                "Indicates this {{object}} is an C-TAG aware
                port of a Customer Bridge.";
              }
              enum "VLANUnawarePort" {
                description
                "Indicates this {{object}} is a VLAN unaware
                member of an {{enum|802.1D-2004|#.Standard}}
                bridge.";
              }
            }
          }
          leaf DefaultUserPriority {
            config true;
            description
            "Bridge Port Default User Priority.";
            type uint32 {
              range "0..7";
            }
          }
          leaf-list PriorityRegeneration {
            config true;
            description
            "{{list}} List items represent user priority
            regeneration values for each ingress user priority
            on this Bridge  Port.";
            type uint32 {
              range "0..7";
            }
            default "0";
            default "1";
            default "2";
            default "3";
            default "4";
            default "5";
            default "6";
            default "7";
          }
          leaf PortState {
            config false;
            description
            "Bridge Port state as defined in 802.1D
            {{bibref|802.1D-2004}} and 802.1Q
            {{bibref|802.1Q-2011}}.";
            type enumeration {
              enum "Disabled";
              enum "Blocking";
              enum "Listening";
              enum "Learning";
              enum "Forwarding";
              enum "Broken";
            }
            default "Disabled";
          }
          leaf PVID {
            config true;
            description
            "For an 802.1D Bridge {{bibref|802.1D-2004}}, this
            parameter MUST be ignored.";
            type int32 {
              range "1..4094";
            }
            default "1";
          }
          leaf TPID {
            config true;
            description
            "*S-TAG 0x9100 = 37120";
            type uint32;
            default "33024";
          }
          leaf AcceptableFrameTypes {
            config true;
            description
            "For an 802.1D {{bibref|802.1D-2004}} Bridge, the
            value of this parameter MUST be {{enum|AdmitAll}}.";
            type enumeration {
              enum "AdmitAll";
              enum "AdmitOnlyVLANTagged";
              enum "AdmitOnlyPrioUntagged";
            }
            default "AdmitAll";
          }
          leaf IngressFiltering {
            config true;
            description
            "For an 802.1D {{bibref|802.1D-2004}} Bridge, the
            value of this parameter MUST be {{false}}.";
            type boolean;
            default "false";
          }
          leaf ServiceAccessPrioritySelection {
            config true;
            description
            "The parameter is applicable to deployments of
            {{object|##.Bridge}} instances that are referenced
            by
            {{param|###.Bridging.ProviderBridge.{i}.SVLANcomponent}}.";
            type boolean;
            default "false";
          }
          leaf-list ServiceAccessPriorityTranslation {
            config true;
            description
            "The parameter is applicable to deployments of
            {{object|##.Bridge}} instances that are referenced
            by
            {{param|###.Bridging.ProviderBridge.{i}.SVLANcomponent}}.";
            type uint32 {
              range "0..7";
            }
            default "0";
            default "1";
            default "2";
            default "3";
            default "4";
            default "5";
            default "6";
            default "7";
          }
          leaf PriorityTagging {
            config true;
            description
            "Only applies on bridge ports that are untagged
            member of one or more VLAN's.";
            type boolean;
            default "false";
          }
          container Stats {
            description
            "The CPE MUST reset the interface's Stats parameters
            (unless otherwise stated in individual object or
            parameter descriptions) either when the interface
            becomes operationally down due to a previous
            administrative down (i.e.  the interface's
            {{param|#.Status}} parameter transitions to a down
            state after the interface is disabled) or when the
            interface becomes administratively up (i.e.  the
            interface's {{param|#.Enable}} parameter
            transitions from {{false}} to {{true}}).
            Administrative and operational interface status is
            discussed in {{bibref|TR-181i2|section 4.2.2}}.";
            leaf BytesSent {
              config false;
              description
              "The total number of bytes transmitted out of the
              interface, including framing characters.";
              type uint64;
            }
            leaf BytesReceived {
              config false;
              description
              "The total number of bytes received on the
              interface, including framing characters.";
              type uint64;
            }
            leaf PacketsSent {
              config false;
              description
              "The total number of packets transmitted out of
              the interface.";
              type uint64;
            }
            leaf PacketsReceived {
              config false;
              description
              "The total number of packets received on the
              interface.";
              type uint64;
            }
            leaf ErrorsSent {
              config false;
              description
              "The total number of outbound packets that could
              not be transmitted because of errors.";
              type uint32;
            }
            leaf ErrorsReceived {
              config false;
              description
              "The total number of inbound packets that
              contained errors preventing them from being
              delivered to a higher-layer protocol.";
              type uint32;
            }
            leaf UnicastPacketsSent {
              config false;
              description
              "The total number of packets requested for
              transmission which were not addressed to a
              multicast or broadcast address at this layer,
              including those that were discarded or not sent.";
              type uint64;
            }
            leaf UnicastPacketsReceived {
              config false;
              description
              "The total number of received packets, delivered
              by this layer to a higher layer, which were not
              addressed to a multicast or broadcast address at
              this layer.";
              type uint64;
            }
            leaf DiscardPacketsSent {
              config false;
              description
              "The total number of outbound packets which were
              chosen to be discarded even though no errors had
              been detected to prevent their being transmitted.
              One possible reason for discarding such a packet
              could be to free up buffer space.";
              type uint32;
            }
            leaf DiscardPacketsReceived {
              config false;
              description
              "The total number of inbound packets which were
              chosen to be discarded even though no errors had
              been detected to  prevent their being delivered.
              One possible reason for discarding such a packet
              could be to free up buffer space.";
              type uint32;
            }
            leaf MulticastPacketsSent {
              config false;
              description
              "The total number of packets that higher-level
              protocols requested for transmission and which
              were addressed to a multicast address at this
              layer, including those that were discarded or not
              sent.";
              type uint64;
            }
            leaf MulticastPacketsReceived {
              config false;
              description
              "The total number of received packets, delivered
              by this layer to a higher layer, which were
              addressed to a multicast address at this layer.";
              type uint64;
            }
            leaf BroadcastPacketsSent {
              config false;
              description
              "The total number of packets that higher-level
              protocols requested for transmission and which
              were addressed to a broadcast address at this
              layer, including those that were discarded or not
              sent.";
              type uint64;
            }
            leaf BroadcastPacketsReceived {
              config false;
              description
              "The total number of received packets, delivered
              by this layer to a higher layer, which were
              addressed to a broadcast address at this layer.";
              type uint64;
            }
            leaf UnknownProtoPacketsReceived {
              config false;
              description
              "The total number of packets received via the
              interface which were discarded because of an
              unknown or unsupported  protocol.";
              type uint32;
            }
          }
          container PriorityCodePoint {
            description
            "The object is applicable to deployments of
            {{object|####.Bridging.ProviderBridge}} where the
            {{object|###.Bridge}} instance is referenced by
            {{param|####.Bridging.ProviderBridge.{i}.SVLANcomponent}}
            or
            {{param|####.Bridging.ProviderBridge.{i}.CVLANcomponents}}
            parameters.";
            leaf PCPSelection {
              config true;
              description
              "This parameter identifies the row in the
              {{param|PCPEncoding}} and {{param|PCPDecoding}}
              parameter lists.  The value of 1 points to the
              8P0D row in the corresponding parameter lists.";
              type uint32 {
                range "1..4";
              }
              default "1";
            }
            leaf UseDEI {
              config true;
              description
              "This parameter controls the processing of the
              drop_eligible field and is described in
              {{bibref|802.1Q-2011|section 6.9.3}}.";
              type boolean;
              default "false";
            }
            leaf RequireDropEncoding {
              config true;
              description
              "This parameter controls the processing of the
              encoding or decoding of the drop_eligible
              component in the PCP field and is described in
              {{bibref|802.1Q-2011|section 8.6.7}}.";
              type boolean;
              default "false";
            }
            leaf-list PCPEncoding {
              config true;
              description
              ":
              [7,7,6,6,5,5,4,4,3,3,2,2,1,1,0,0],[7,7,6,6,5,4,5,4,3,3,2,2,1,1,0,0],[7,7,6,6,5,4,5,4,3,2,3,2,1,1,0,0],[7,7,6,6,5,4,5,4,3,2,3,2,1,0,1,0]";
              type string {
                length "31";
                pattern "([0-7],){15}[0-7]";
              }
            }
            leaf-list PCPDecoding {
              config true;
              description
              ":
              [7,0,6,0,5,0,4,0,3,0,2,0,1,0,0,0],[7,0,6,0,4,0,4,1,3,0,2,0,1,0,0,0],[7,0,6,0,4,0,4,1,2,0,2,1,1,0,0,0],[7,0,6,0,4,0,4,1,2,0,2,1,0,0,0,1]";
              type string {
                length "15";
                pattern "([0-7],[0-1],){7}[0-7],[0-1]";
              }
            }
          }
        }
        list VLAN {
          key "VLANID";
          unique "Alias";
          config true;
          description
          "This table only applies to an 802.1Q
          {{bibref|802.1Q-2011}} Bridge.";
          leaf Enable {
            config true;
            description
            "Enables or disables this VLAN table entry.";
            type boolean;
            default "false";
          }
          leaf Alias {
            config true;
            description
            "{{datatype|expand}}";
            type Alias;
          }
          leaf Name {
            config true;
            description
            "Human-readable name for this VLAN table entry.";
            type string {
              length "0..64";
            }
          }
          leaf VLANID {
            config true;
            description
            "VLAN ID of the entry.";
            type int32 {
              range "1..4094";
            }
          }
        }
        list VLANPort {
          key "VLAN Port";
          unique "Alias";
          config true;
          description
          "Note: The {{object}} table includes unique key
          parameters that are strong references.  If a strongly
          referenced object is deleted, the CPE will set the
          referencing parameter to {{empty}}. However, doing so
          under these circumstances might cause the updated
          {{object}} row to then violate the table's unique key
          constraint; if this occurs, the CPE MUST disable the
          offending {{object}} row.";
          leaf Enable {
            config true;
            description
            "Enables or disables this {{object}} entry.";
            type boolean;
            default "false";
          }
          leaf Alias {
            config true;
            description
            "{{datatype|expand}}";
            type Alias;
          }
          leaf VLAN {
            config true;
            description
            "{{reference}}  Specifies the VLAN for which port
            membership is expressed.";
            type string {
              length "0..256";
            }
          }
          leaf Port {
            config true;
            description
            "{{reference}}  Specifies the bridge port that is
            member of the VLAN.";
            type string {
              length "0..256";
            }
          }
          leaf Untagged {
            config true;
            description
            "Enables or disables untagged port membership to the
            VLAN and determines whether egress frames for this
            VLAN are sent untagged or tagged.";
            type boolean;
          }
        }
      }
      list Filter {
        key "Alias";
        config true;
        description
        "Several of this object's parameters specify DHCP option
        values.  Some cases are version neutral (the parameter
        can apply to both DHCPv4 and DHCPv6), but in other
        cases the representation of the option is different for
        DHCPv4 and DHCPv6, so it is necessary to define
        separate DHCPv4-specific and DHCPv6-specific
        parameters.  Therefore, an instance of this object that
        uses DHCP option values as filter criteria will be
        associated with either DHCPv4 or DHCPv6, as indicated
        by the {{param|DHCPType}} parameter.";
        leaf Enable {
          config true;
          description
          "Enables or disables this Filter table entry.";
          type boolean;
          default "false";
        }
        leaf Alias {
          config true;
          description
          "{{datatype|expand}}";
          type Alias;
        }
        leaf Status {
          config false;
          description
          "If the Bridge VLAN table is supported, but none of
          its entries correspond to {{param|VLANIDFilter}}, or
          if such an entry exists but is disabled, {{param}}
          MUST NOT indicate {{enum|Enabled}}.";
          type enumeration {
            enum "Disabled";
            enum "Enabled";
            enum "Error_Misconfigured";
            enum "Error";
          }
          default "Disabled";
        }
        leaf Bridge {
          config true;
          description
          "Defines the Bridge or Bridge VLAN to which ingress
          frames will be classified based upon matches of the
          classification criteria.";
          type string {
            length "0..256";
          }
        }
        leaf Order {
          config true;
          description
          "The value of {{param}} on creation of a {{object}}
          table entry MUST be one greater than the largest
          current value (initially assigned the lowest
          precedence).";
          type uint32 {
            range "1..max";
          }
        }
        leaf Interface {
          config true;
          description
          "Defines the Bridge Port on which ingress frame
          classification will occur.";
          type string {
            length "0..256";
          }
        }
        leaf DHCPType {
          config true;
          description
          "If {{param}} is {{enum|DHCPv4}}, then {{object}}
          parameters that are DHCPv6-specific are ignored.  If
          {{param}} is {{enum|DHCPv6}}, then {{object}}
          parameters that are DHCPv4-specific are ignored.";
          type enumeration {
            enum "DHCPv4";
            enum "DHCPv6";
          }
          default "DHCPv4";
        }
        leaf VLANIDFilter {
          config true;
          description
          "For an 802.1D {{bibref|802.1D-2004}} Bridge, which
          has no concept of VLANs, the VLAN ID MUST be ''0''.";
          type uint32 {
            range "0..4094";
          }
          default "0";
        }
        leaf-list EthertypeFilterList {
          config true;
          description
          "Note that neither 802.1D {{bibref|802.1D-2004}} nor
          802.1Q {{bibref|802.1Q-2011}} support classification
          based on  Ethertype.";
          type uint32;
        }
        leaf EthertypeFilterExclude {
          config true;
          description
          "Note that neither 802.1D {{bibref|802.1D-2004}} nor
          802.1Q {{bibref|802.1Q-2011}} support classification
          based on  Ethertype.";
          type boolean;
          default "true";
        }
        leaf-list SourceMACAddressFilterList {
          config true;
          description
          "Note that neither 802.1D {{bibref|802.1D-2004}} nor
          802.1Q {{bibref|802.1Q-2011}} support classification
          based on source MAC  address.";
          type string;
        }
        leaf SourceMACAddressFilterExclude {
          config true;
          description
          "Note that neither 802.1D {{bibref|802.1D-2004}} nor
          802.1Q {{bibref|802.1Q-2011}} support classification
          based on source MAC  address.";
          type boolean;
          default "true";
        }
        leaf-list DestMACAddressFilterList {
          config true;
          description
          "For example, the list might be: ''01:02:03:04:05:06,
          1:22:33:00:00:00/FF:FF:FF:00:00:00,
          88:77:66:55:44:33''";
          type string;
        }
        leaf DestMACAddressFilterExclude {
          config true;
          description
          "If {{true}}, on ingress to the interfaces associated
          with this Filter, the Bridge admits all packets
          except those packets whose  destination MAC Address
          matches one of the {{param|DestMACAddressFilterList}}
          entries.  If the {{param|DestMACAddressFilterList}}
          is  empty, packets are admitted regardless of MAC
          address.";
          type boolean;
          default "true";
        }
        leaf SourceMACFromVendorClassIDFilter {
          config true;
          description
          "Note: This parameter is DHCPv4-specific.  It only
          applies when {{param|DHCPType}} is
          {{enum|DHCPv4|DHCPType}}.";
          type string {
            length "0..255";
          }
        }
        leaf SourceMACFromVendorClassIDFilterv6 {
          config true;
          description
          "Note: This parameter is DHCPv6-specific.  It only
          applies when {{param|DHCPType}} is
          {{enum|DHCPv6|DHCPType}}.";
          type yang:hex-string {
            length "0..65535";
          }
        }
        leaf SourceMACFromVendorClassIDFilterExclude {
          config true;
          description
          "Note that neither 802.1D {{bibref|802.1D-2004}} nor
          802.1Q {{bibref|802.1Q-2011}} support classification
          based on source MAC address";
          type boolean;
          default "true";
        }
        leaf SourceMACFromVendorClassIDMode {
          config true;
          description
          "Note that neither 802.1D {{bibref|802.1D-2004}} nor
          802.1Q {{bibref|802.1Q-2011}} support classification
          based on source MAC  address.";
          type enumeration {
            enum "Exact";
            enum "Prefix";
            enum "Suffix";
            enum "Substring";
          }
          default "Exact";
        }
        leaf DestMACFromVendorClassIDFilter {
          config true;
          description
          "Note: This parameter is DHCPv4-specific.  It only
          applies when {{param|DHCPType}} is
          {{enum|DHCPv4|DHCPType}}.";
          type string {
            length "0..255";
          }
        }
        leaf DestMACFromVendorClassIDFilterv6 {
          config true;
          description
          "Note: This parameter is DHCPv6-specific.  It only
          applies when {{param|DHCPType}} is
          {{enum|DHCPv6|DHCPType}}.";
          type yang:hex-string {
            length "0..65535";
          }
        }
        leaf DestMACFromVendorClassIDFilterExclude {
          config true;
          description
          "If {{true}}, on ingress to the interfaces associated
          with this Filter, the Bridge admits all packets
          except those packets whose destination MAC Address
          matches that of a LAN device previously identified as
          described in {{param|DestMACFromVendorClassIDFilter}}
          (for {{enum|DHCPv4|DHCPType}}) or
          {{param|DestMACFromVendorClassIDFilterv6}} (for
          {{enum|DHCPv6|DHCPType}}). If this corresponding
          filter parameter is {{empty}}, packets are admitted
          regardless of MAC address.";
          type boolean;
          default "true";
        }
        leaf DestMACFromVendorClassIDMode {
          config true;
          description
          "For example, if
          {{param|DestMACFromVendorClassIDFilter}} is
          ''Example'' then an Option 60 value of \"Example
          device\" will match with  {{param}} values of
          {{enum|Prefix}} or {{enum|Substring}}, but not with
          {{enum|Exact}} or {{enum|Suffix}}.";
          type enumeration {
            enum "Exact";
            enum "Prefix";
            enum "Suffix";
            enum "Substring";
          }
          default "Exact";
        }
        leaf SourceMACFromClientIDFilter {
          config true;
          description
          "Note: DHCPv6 Option 1 (Client Identifier) is
          sometimes referred to as ''DUID''.";
          type yang:hex-string {
            length "0..65535";
          }
        }
        leaf SourceMACFromClientIDFilterExclude {
          config true;
          description
          "Note that neither 802.1D {{bibref|802.1D-2004}} nor
          802.1Q {{bibref|802.1Q-2011}} support classification
          based on source MAC  address.";
          type boolean;
          default "true";
        }
        leaf DestMACFromClientIDFilter {
          config true;
          description
          "Note: DHCPv6 Option 1 (Client Identifier) is
          sometimes referred to as ''DUID''.";
          type yang:hex-string {
            length "0..65535";
          }
        }
        leaf DestMACFromClientIDFilterExclude {
          config true;
          description
          "If {{true}}, on ingress to the interfaces associated
          with this Filter, the Bridge admits all packets
          except those packets whose destination MAC Address
          matches that of a LAN device previously identified as
          described in {{param|DestMACFromClientIDFilter}}.  If
          the {{param|DestMACFromClientIDFilter}} is {{empty}},
          packets are admitted regardless of MAC address.";
          type boolean;
          default "true";
        }
        leaf SourceMACFromUserClassIDFilter {
          config true;
          description
          "Note: This parameter is DHCP version neutral.  The
          specific DHCP version in use with this parameter is
          indicated by {{param|DHCPType}}.";
          type yang:hex-string {
            length "0..65535";
          }
        }
        leaf SourceMACFromUserClassIDFilterExclude {
          config true;
          description
          "Note that neither 802.1D {{bibref|802.1D-2004}} nor
          802.1Q {{bibref|802.1Q-2011}} support classification
          based on source MAC address.";
          type boolean;
          default "true";
        }
        leaf DestMACFromUserClassIDFilter {
          config true;
          description
          "Note: This parameter is DHCP version neutral.  The
          specific DHCP version in use with this parameter is
          indicated by {{param|DHCPType}}.";
          type yang:hex-string {
            length "0..65535";
          }
        }
        leaf DestMACFromUserClassIDFilterExclude {
          config true;
          description
          "If {{true}}, on ingress to the interfaces associated
          with this Filter, the Bridge admits all packets
          except those packets whose destination MAC Address
          matches that of a LAN device previously identified as
          described in {{param|DestMACFromUserClassIDFilter}}.
          If the {{param|DestMACFromUserClassIDFilter}} is
          {{empty}}, packets are admitted regardless of MAC
          address.";
          type boolean;
          default "true";
        }
        leaf DestIP {
          config true;
          description
          "Destination IP address.  {{empty}} indicates this
          criterion is not used for classification.";
          type inet:ip-address;
        }
        leaf DestMask {
          config true;
          description
          "Destination IP address mask, represented as an IP
          routing prefix using CIDR notation [RFC4632]. The IP
          address part MUST be {{empty}} (and, if specified,
          MUST be ignored).";
          type inet:ip-prefix;
        }
        leaf DestIPExclude {
          config true;
          description
          "If {{true}}, the class includes all packets except
          those that match the (masked) DestIP entry, if
          specified.";
          type boolean;
          default "false";
        }
        leaf SourceIP {
          config true;
          description
          "Source IP address.  {{empty}} indicates this
          criterion is not used for classification.";
          type inet:ip-address;
        }
        leaf SourceMask {
          config true;
          description
          "Source IP address mask, represented as an IP routing
          prefix using CIDR notation [RFC4632]. The IP address
          part MUST be an empty string (and, if specified, MUST
          be ignored).";
          type inet:ip-prefix;
        }
        leaf SourceIPExclude {
          config true;
          description
          "If {{true}}, the class includes all packets except
          those that match the (masked) {{param|SourceIP}}
          entry, if specified.";
          type boolean;
          default "false";
        }
        leaf Protocol {
          config true;
          description
          "Protocol number.  A value of -1 indicates this
          criterion is not used for classification.";
          type int32 {
            range "-1..255";
          }
          default "-1";
        }
        leaf ProtocolExclude {
          config true;
          description
          "If {{true}}, the class includes all packets except
          those that match the {{param|Protocol}} entry, if
          specified.";
          type boolean;
          default "false";
        }
        leaf DestPort {
          config true;
          description
          "Destination port number.  A value of -1 indicates
          this criterion is not used for classification.";
          type int32 {
            range "-1..65535";
          }
          default "-1";
        }
        leaf DestPortRangeMax {
          config true;
          description
          "A value of -1 indicates that no port range is
          specified.";
          type int32 {
            range "-1..65535";
          }
          default "-1";
        }
        leaf DestPortExclude {
          config true;
          description
          "If {{true}}, the class includes all packets except
          those that match the {{param|DestPort}} entry (or
          port range), if  specified.";
          type boolean;
          default "false";
        }
        leaf SourcePort {
          config true;
          description
          "Source port number.  A value of -1 indicates this
          criterion is not used for classification.";
          type int32 {
            range "-1..65535";
          }
          default "-1";
        }
        leaf SourcePortRangeMax {
          config true;
          description
          "A value of -1 indicates that no port range is
          specified.";
          type int32 {
            range "-1..65535";
          }
          default "-1";
        }
        leaf SourcePortExclude {
          config true;
          description
          "If {{true}}, the class includes all packets except
          those that match the {{param|SourcePort}} entry (or
          port range), if  specified.";
          type boolean;
          default "false";
        }
      }
      list ProviderBridge {
        key "Alias";
        config true;
        description
        "When {{param|Type}} is configured with value of
        {{enum|S-VLAN|Type}} only VLAN tags from the S-VLAN
        component are utilized.";
        leaf Enable {
          config true;
          description
          "Enables or disables this {{object}}.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Alias {
          config true;
          description
          "A non-volatile handle used to reference this
          instance.  This parameter provides a mechanism for an
          ACS to label this instance for future reference.  An
          initial unique value MUST be assigned when the CPE
          creates an instance of this object.";
          type string {
            length "0..64";
          }
        }
        leaf Type {
          config true;
          description
          "Selects the standard supported by this {{object}}
          table entry.";
          type enumeration {
            enum "S-VLAN" {
              description
              "Provider Bridge conforming to
              {{bibref|802.1Q-2011|5.10.1 S-VLAN Bridge
              conformance}}";
            }
            enum "PE" {
              description
              "Provider Bridge conforming to
              {{bibref|802.1Q-2011|5.10.2 Provider Edge Bridge
              conformance}}";
            }
          }
        }
        leaf SVLANcomponent {
          config true;
          description
          "{{reference|a {{object|#.Bridge}} instance that
          specifies the S-VLAN component for the {{object}}}}";
          type string {
            length "0..256";
          }
        }
        leaf-list CVLANcomponents {
          config true;
          description
          "{{list}} {{reference|a {{object|#.Bridge}} instance
          that specifies a C-VLAN component for the
          {{object}}}}";
          type string {
            length "0..256";
          }
        }
      }
    }
    container PPP {
      description
      "Point-to-Point Protocol {{bibref|RFC1661}}. This object
      contains the {{object|Interface}} table.";
      leaf InterfaceNumberOfEntries {
        config false;
        description
        "{{numentries}}";
        type uint32;
      }
      leaf-list SupportedNCPs {
        config false;
        description
        "Note that {{enum|IPv6CP}} is an IPv6 capability.";
        type enumeration {
          enum "ATCP" {
            description
            "AppleTalk Control Protocol {{bibref|RFC1378}}";
          }
          enum "IPCP" {
            description
            "{{bibref|RFC1332}}";
          }
          enum "IPXCP" {
            description
            "{{bibref|RFC1552}}";
          }
          enum "NBFCP" {
            description
            "{{bibref|RFC2097}}";
          }
          enum "IPv6CP" {
            description
            "{{bibref|RFC5072}}";
          }
        }
      }
      list Interface {
        key "Name";
        unique "Alias";
        config true;
        description
        "PPP interface table (a stackable interface object as
        described in {{bibref|TR-181i2|Section 4.2}}).";
        leaf Enable {
          config true;
          description
          "This parameter is based on ''ifAdminStatus'' from
          {{bibref|RFC2863}}.";
          type boolean;
          default "false";
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
          default "Down";
        }
        leaf Alias {
          config true;
          description
          "{{datatype|expand}}";
          type Alias;
        }
        leaf Name {
          config true;
          description
          "The textual name of the interface as assigned by the
          CPE.";
          type string {
            length "0..64";
          }
        }
        leaf LastChange {
          config false;
          description
          "The accumulated time in {{units}} since the interface
          entered its current operational state.";
          type uint32;
        }
        leaf-list LowerLayers {
          config true;
          description
          "{{list}} {{reference|an interface object that is
          stacked immediately below this interface object}}
          See {{bibref|TR-181i2|Section 4.2.1}}.";
          type string;
        }
        leaf Reset {
          config true;
          description
          "Reset on a disabled interface is a no-op (not an
          error).";
          type boolean;
          default "false";
        }
        leaf ConnectionStatus {
          config false;
          description
          "Current status of the connection.";
          type enumeration {
            enum "Unconfigured";
            enum "Connecting";
            enum "Authenticating";
            enum "Connected";
            enum "PendingDisconnect";
            enum "Disconnecting";
            enum "Disconnected";
          }
        }
        leaf LastConnectionError {
          config false;
          description
          "The cause of failure for the last connection setup
          attempt.";
          type enumeration {
            enum "ERROR_NONE";
            enum "ERROR_ISP_TIME_OUT";
            enum "ERROR_COMMAND_ABORTED";
            enum "ERROR_NOT_ENABLED_FOR_INTERNET";
            enum "ERROR_BAD_PHONE_NUMBER";
            enum "ERROR_USER_DISCONNECT";
            enum "ERROR_ISP_DISCONNECT";
            enum "ERROR_IDLE_DISCONNECT";
            enum "ERROR_FORCED_DISCONNECT";
            enum "ERROR_SERVER_OUT_OF_RESOURCES";
            enum "ERROR_RESTRICTED_LOGON_HOURS";
            enum "ERROR_ACCOUNT_DISABLED";
            enum "ERROR_ACCOUNT_EXPIRED";
            enum "ERROR_PASSWORD_EXPIRED";
            enum "ERROR_AUTHENTICATION_FAILURE";
            enum "ERROR_NO_DIALTONE";
            enum "ERROR_NO_CARRIER";
            enum "ERROR_NO_ANSWER";
            enum "ERROR_LINE_BUSY";
            enum "ERROR_UNSUPPORTED_BITSPERSECOND";
            enum "ERROR_TOO_MANY_LINE_ERRORS";
            enum "ERROR_IP_CONFIGURATION";
            enum "ERROR_UNKNOWN";
          }
        }
        leaf AutoDisconnectTime {
          config true;
          description
          "The time in {{units}} since the establishment of the
          connection after which connection termination is
          automatically initiated by the CPE.  This occurs
          irrespective of whether the connection is being used
          or not.  A value of 0 (zero) indicates that the
          connection is not to be shut down automatically.";
          type uint32;
        }
        leaf IdleDisconnectTime {
          config true;
          description
          "The time in {{units}} that if the connection remains
          idle, the CPE automatically terminates the
          connection.  A  value of 0 (zero) indicates that the
          connection is not to be shut down automatically.";
          type uint32;
        }
        leaf WarnDisconnectDelay {
          config true;
          description
          "Time in {{units}} the {{param|ConnectionStatus}}
          remains in the
          {{enum|PendingDisconnect|ConnectionStatus}} state
          before transitioning to disconnecting state to drop
          the connection.";
          type uint32;
        }
        leaf Username {
          config true;
          description
          "Username to be used for authentication.";
          type string {
            length "0..64";
          }
        }
        leaf Password {
          config true;
          description
          "Password to be used for authentication.";
          type string {
            length "0..64";
          }
        }
        leaf EncryptionProtocol {
          config false;
          description
          "Describes the PPP encryption protocol.";
          type enumeration {
            enum "None";
            enum "MPPE";
          }
        }
        leaf CompressionProtocol {
          config false;
          description
          "Describes the PPP compression protocol.";
          type enumeration {
            enum "None";
            enum "Van Jacobson" {
              description
              "{{bibref|RFC1332}}";
            }
            enum "STAC LZS" {
              description
              "{{bibref|RFC1974}}";
            }
          }
        }
        leaf AuthenticationProtocol {
          config false;
          description
          "Describes the PPP authentication protocol.";
          type enumeration {
            enum "PAP";
            enum "CHAP";
            enum "MS-CHAP";
          }
        }
        leaf MaxMRUSize {
          config true;
          description
          "The maximum allowed size of frames sent from the
          remote peer.";
          type uint32 {
            range "64..65535";
          }
          default "1500";
        }
        leaf CurrentMRUSize {
          config false;
          description
          "The current MRU in use over this connection.";
          type uint32 {
            range "64..65535";
          }
        }
        leaf ConnectionTrigger {
          config true;
          description
          "Note that the reason for a PPP connection becoming
          disconnected to begin with might be either external
          to the CPE, such as  termination by the BRAS or
          momentary disconnection of the physical interface, or
          internal to the CPE, such as use of the
          {{param|IdleDisconnectTime}} and/or
          {{param|AutoDisconnectTime}} parameters in this
          object.";
          type enumeration {
            enum "OnDemand" {
              description
              "If this PPP connection is disconnected for any
              reason, it is to remain disconnected until the
              CPE has one  or more packets to communicate over
              this connection, at which time the CPE
              automatically attempts to reestablish the
              connection.";
            }
            enum "AlwaysOn" {
              description
              "If this PPP connection is disconnected for any
              reason, the CPE automatically attempts to
              reestablish the  connection (and continues to
              attempt to reestablish the connection as long it
              remains disconnected).";
            }
            enum "Manual" {
              description
              "If this PPP connection is disconnected for any
              reason, it is to remain disconnected until the
              user of the  CPE explicitly instructs the CPE to
              reestablish the connection.";
            }
          }
        }
        leaf LCPEcho {
          config false;
          description
          "PPP LCP Echo period in {{units}}.";
          type uint32;
        }
        leaf LCPEchoRetry {
          config false;
          description
          "Number of PPP LCP Echo retries within an echo period.";
          type uint32;
        }
        leaf IPCPEnable {
          config true;
          description
          "Enables or disables IPCP ({{bibref|RFC1332}}) on this
          interface.  If this parameter is present,
          {{enum|IPCP|#.SupportedNCPs}} MUST be included in
          {{param|#.SupportedNCPs}}.";
          type boolean;
        }
        leaf IPv6CPEnable {
          config true;
          description
          "Enables or disables IPv6CP ({{bibref|RFC5072}}) on
          this interface.  If this parameter is present,
          {{enum|IPv6CP|#.SupportedNCPs}} MUST be included in
          {{param|#.SupportedNCPs}}.";
          type boolean;
        }
        container PPPoE {
          description
          "PPPoE is only applicable when the lower layer
          provides Ethernet frames, e.g.  ATM with EoA, PTM, or
          anything else that supports an Ethernet MAC.";
          leaf SessionID {
            config false;
            description
            "Represents the PPPoE Session ID.";
            type uint32 {
              range "1..max";
            }
          }
          leaf ACName {
            config true;
            description
            "PPPoE Access Concentrator.";
            type string {
              length "0..256";
            }
          }
          leaf ServiceName {
            config true;
            description
            "PPPoE Service Name.";
            type string {
              length "0..256";
            }
          }
        }
        container IPCP {
          description
          "IP Control Protocol (IPCP) client object for this PPP
          interface {{bibref|RFC1332}}. {{object}} only applies
          to IPv4.";
          leaf LocalIPAddress {
            config false;
            description
            "The local IPv4 address for this connection received
            via IPCP.";
            type inet:ipv4-address;
          }
          leaf RemoteIPAddress {
            config false;
            description
            "The remote IPv4 address for this connection
            received via IPCP.";
            type inet:ipv4-address;
          }
          leaf-list DNSServers {
            config false;
            description
            "{{list}} Items represent DNS Server IPv4
            address(es) received via IPCP {{bibref|RFC1877}}.";
            type inet:ipv4-address;
          }
          leaf PassthroughEnable {
            config true;
            description
            "If {{true}}, the PPP Interface retrieved
            information is propagated to the parameters in the
            referenced {{param|PassthroughDHCPPool}} object,
            replacing any existing configuration (including
            ''MinAddress'', ''MaxAddress'', ''SubnetMask'',
            ''IPRouters'', and ''DNSServers'').";
            type boolean;
            default "false";
          }
          leaf PassthroughDHCPPool {
            config true;
            description
            "{{reference}}When {{param}} is set to {{empty}},
            {{param|PassthroughEnable}} MUST be set to
            {{false}} (i.e.  passthrough can not be enabled
            without a pool reference specified).";
            type string {
              length "0..256";
            }
          }
        }
        container IPv6CP {
          description
          "IPv6 Control Protocol (IPv6CP) client object for this
          PPP interface {{bibref|RFC5072}}. {{object}} only
          applies to IPv6.";
          leaf LocalInterfaceIdentifier {
            config false;
            description
            "The identifier is represented as the rightmost 64
            bits of an IPv6 address (the leftmost 64 bits MUST
            be zero and MUST be ignored by the recipient).";
            type inet:ipv6-address;
          }
          leaf RemoteInterfaceIdentifier {
            config false;
            description
            "The identifier is represented as the rightmost 64
            bits of an IPv6 address (the leftmost 64 bits MUST
            be zero and MUST be ignored by the recipient).";
            type inet:ipv6-address;
          }
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "The total number of packets that higher-level
            protocols requested for transmission and which were
            addressed to a broadcast address at this layer,
            including those that were discarded or not sent.";
            type uint64;
          }
          leaf BroadcastPacketsReceived {
            config false;
            description
            "The total number of received packets, delivered by
            this layer to a higher layer, which were addressed
            to a broadcast address at this layer.";
            type uint64;
          }
          leaf UnknownProtoPacketsReceived {
            config false;
            description
            "The total number of packets received via the
            interface which were discarded because of an
            unknown or unsupported  protocol.";
            type uint32;
          }
        }
        container PPPoA {
          description
          "This object is OBSOLETED because it contains no
          standard parameters and its existence causes
          confusion.";
        }
      }
    }
    container IP {
      description
      "IP object that contains the {{object|Interface}},
      {{object|ActivePort}}, and {{object|Diagnostics}}
      objects.";
      leaf IPv4Capable {
        config false;
        description
        "Indicates whether the device is IPv4 capable.";
        type boolean;
      }
      leaf IPv4Enable {
        config true;
        description
        "When {{false}}, IP interfaces that had been
        operationally up and passing IPv4 packets will now no
        longer be able to do so, and will be operationally down
        (unless also attached to an enabled IPv6 stack).";
        type boolean;
      }
      leaf IPv4Status {
        config false;
        description
        "The {{enum|Error}} value MAY be used by the CPE to
        indicate a locally defined error condition.";
        type enumeration {
          enum "Disabled";
          enum "Enabled";
          enum "Error";
        }
      }
      leaf IPv6Capable {
        config false;
        description
        "Note: If {{false}}, it is expected that IPv6-related
        parameters, enumeration values, etc will not be
        implemented by the device.";
        type boolean;
      }
      leaf IPv6Enable {
        config true;
        description
        "When {{false}}, IP interfaces that had been
        operationally up and passing IPv6 packets will now no
        longer be able to do so, and will be operationally down
        (unless also attached to an enabled IPv4 stack).";
        type boolean;
      }
      leaf IPv6Status {
        config false;
        description
        "The {{enum|Error}} value MAY be used by the CPE to
        indicate a locally defined error condition.";
        type enumeration {
          enum "Disabled";
          enum "Enabled";
          enum "Error";
        }
      }
      leaf ULAPrefix {
        config true;
        description
        "The ULA /48 prefix {{bibref|RFC4193|Section 3}}.";
        type inet:ipv6-prefix;
      }
      leaf InterfaceNumberOfEntries {
        config false;
        description
        "{{numentries}}";
        type uint32;
      }
      leaf ActivePortNumberOfEntries {
        config false;
        description
        "{{numentries}}";
        type uint32;
      }
      list Interface {
        key "Name";
        unique "Alias";
        config true;
        description
        "Note that {{enum|Tunnel|Type}} and
        {{enum|Tunneled|Type}} IP interfaces are part of a
        legacy mechanism that is only used for
        {{object|##.IPv6rd}}, {{object|##.DSLite}} and
        {{object|##.IPsec}} tunnels and MUST NOT be used in any
        other context.  For all other tunneling mechanisms
        {{enum|Normal|Type}} IP interfaces are stacked above
        technology-specific Tunnel Interfaces, e.g.  above
        {{object|##.GRE.Tunnel.{i}.Interface}} or
        {{object|##.MAP.Domain.{i}.Interface}} objects.";
        leaf Enable {
          config true;
          description
          "This parameter is based on ''ifAdminStatus'' from
          {{bibref|RFC2863}}.";
          type boolean;
          default "false";
        }
        leaf IPv4Enable {
          config true;
          description
          "Note that {{param}} is independent of
          {{param|Enable}}, and that to administratively enable
          an interface for IPv4 it is necessary for both
          {{param|Enable}} and {{param}} to be {{true}}.";
          type boolean;
        }
        leaf IPv6Enable {
          config true;
          description
          "Note that {{param}} is independent of
          {{param|Enable}}, and that to administratively enable
          an interface for IPv6 it is necessary for both
          {{param|Enable}} and {{param}} to be {{true}}.";
          type boolean;
        }
        leaf ULAEnable {
          config true;
          description
          "Controls whether or not ULAs {{bibref|RFC4193}} are
          generated and used on this interface.";
          type boolean;
          default "false";
        }
        leaf Status {
          config false;
          description
          "This parameter is based on ''ifOperStatus'' from
          {{bibref|RFC2863}}.";
          type enumeration {
            enum "Up";
            enum "Down";
            enum "Unknown";
            enum "Dormant";
            enum "NotPresent";
            enum "LowerLayerDown";
            enum "Error";
          }
          default "Down";
        }
        leaf Alias {
          config true;
          description
          "{{datatype|expand}}";
          type Alias;
        }
        leaf Name {
          config true;
          description
          "The textual name of the interface as assigned by the
          CPE.";
          type string {
            length "0..64";
          }
        }
        leaf LastChange {
          config false;
          description
          "The accumulated time in {{units}} since the interface
          entered its current operational state.";
          type uint32;
        }
        leaf-list LowerLayers {
          config true;
          description
          "{{param}} MUST be {{empty}} and read-only when
          {{param|Type}} is {{enum|Loopback|Type}},
          {{enum|Tunnel|Type}}, or {{enum|Tunneled|Type}}.";
          type string;
        }
        leaf Router {
          config true;
          description
          "{{reference}} The ''Router'' instance that is
          associated with this IP Interface entry.";
          type string {
            length "0..256";
          }
        }
        leaf Reset {
          config true;
          description
          "Reset on a disabled interface is a no-op (not an
          error).";
          type boolean;
          default "false";
        }
        leaf MaxMTUSize {
          config true;
          description
          "The maximum transmission unit (MTU); the largest
          allowed size of an IP packet (including IP headers,
          but excluding lower layer headers such as Ethernet,
          PPP, or PPPoE headers) that is allowed to be
          transmitted by or through this device.";
          type uint32 {
            range "64..65535";
          }
        }
        leaf Type {
          config false;
          description
          "For {{enum|Loopback}}, {{enum|Tunnel}}, and
          {{enum|Tunneled}} IP interface objects, the
          {{param|LowerLayers}} parameter MUST be {{empty}}.";
          type enumeration {
            enum "Normal";
            enum "Loopback";
            enum "Tunnel" {
              description
              "Only used with legacy
              ({{enum|Tunnel}},{{enum|Tunneled}}) IP interface
              pairs";
            }
            enum "Tunneled" {
              description
              "Only used with legacy
              ({{enum|Tunnel}},{{enum|Tunneled}}) IP interface
              pairs";
            }
          }
          default "Normal";
        }
        leaf Loopback {
          config true;
          description
          "Support for manipulating loopback interfaces is
          OPTIONAL.";
          type boolean;
          default "false";
        }
        leaf IPv4AddressNumberOfEntries {
          config false;
          description
          "{{numentries}}";
          type uint32;
        }
        leaf IPv6AddressNumberOfEntries {
          config false;
          description
          "{{numentries}}";
          type uint32;
        }
        leaf IPv6PrefixNumberOfEntries {
          config false;
          description
          "{{numentries}}";
          type uint32;
        }
        leaf AutoIPEnable {
          config true;
          description
          "When auto-IP is enabled on an interface, an
          {{object|IPv4Address}} object will dynamically be
          created and configured with auto-IP  parameter
          values.  The exact conditions under which an auto-IP
          address is created (e.g.  always when enabled or only
          in absence of  dynamic IP addressing) is
          implementation specific.";
          type boolean;
          default "false";
        }
        leaf TWAMPReflectorNumberOfEntries {
          config false;
          description
          "{{numentries}}";
          type uint32;
        }
        list IPv4Address {
          key "IPAddress SubnetMask";
          unique "Alias";
          config true;
          description
          "IPv4 address table.  Entries are auto-created and
          auto-deleted as IP addresses are added and deleted
          via DHCP, auto-IP, or IPCP. Static entries are
          created and configured by the ACS.";
          leaf Enable {
            config true;
            description
            "Enables or disables this IPv4 address.";
            type boolean;
            default "false";
          }
          leaf Status {
            config false;
            description
            "The {{enum|Error}} value MAY be used by the CPE to
            indicate a locally defined error condition.";
            type enumeration {
              enum "Disabled";
              enum "Enabled";
              enum "Error_Misconfigured";
              enum "Error";
            }
            default "Disabled";
          }
          leaf Alias {
            config true;
            description
            "This parameter can only be modified if
            {{param|AddressingType}} is
            {{enum|Static|AddressingType}}.";
            type Alias;
          }
          leaf IPAddress {
            config true;
            description
            "This parameter can only be modified if the
            {{param|AddressingType}} is
            {{enum|Static|AddressingType}}.";
            type inet:ipv4-address;
          }
          leaf SubnetMask {
            config true;
            description
            "This parameter can only be modified if the
            {{param|AddressingType}} is
            {{enum|Static|AddressingType}}.";
            type inet:ipv4-address;
          }
          leaf AddressingType {
            config false;
            description
            "Addressing method used to assign the IP address.
            {{enum}}";
            type enumeration {
              enum "DHCP";
              enum "IKEv2" {
                description
                "Assigned by IKEv2 {{bibref|RFC5996}}.";
              }
              enum "AutoIP";
              enum "IPCP";
              enum "Static";
            }
            default "Static";
          }
        }
        container Stats {
          description
          "The CPE MUST reset the interface's Stats parameters
          (unless otherwise stated in individual object or
          parameter descriptions) either when the interface
          becomes operationally down due to a previous
          administrative down (i.e.  the interface's
          {{param|#.Status}} parameter transitions to a down
          state after the interface is disabled) or when the
          interface becomes administratively up (i.e.  the
          interface's {{param|#.Enable}} parameter transitions
          from {{false}} to {{true}}). Administrative and
          operational interface status is discussed in
          {{bibref|TR-181i2|section 4.2.2}}.";
          leaf BytesSent {
            config false;
            description
            "The total number of bytes transmitted out of the
            interface, including framing characters.";
            type uint64;
          }
          leaf BytesReceived {
            config false;
            description
            "The total number of bytes received on the
            interface, including framing characters.";
            type uint64;
          }
          leaf PacketsSent {
            config false;
            description
            "The total number of packets transmitted out of the
            interface.";
            type uint64;
          }
          leaf PacketsReceived {
            config false;
            description
            "The total number of packets received on the
            interface.";
            type uint64;
          }
          leaf ErrorsSent {
            config false;
            description
            "The total number of outbound packets that could not
            be transmitted because of errors.";
            type uint32;
          }
          leaf ErrorsReceived {
            config false;
            description
            "The total number of inbound packets that contained
            errors preventing them from being delivered to a
            higher-layer protocol.";
            type uint32;
          }
          leaf UnicastPacketsSent {
            config false;
            description
            "The total number of packets requested for
            transmission which were not addressed to a
            multicast or broadcast address at this layer,
            including those that were discarded or not sent.";
            type uint64;
          }
          leaf UnicastPacketsReceived {
            config false;
            description
            "The total number of received packets, delivered by
            this layer to a higher layer, which were not
            addressed to a multicast or broadcast address at
            this layer.";
            type uint64;
          }
          leaf DiscardPacketsSent {
            config false;
            description
            "The total number of outbound packets which were
            chosen to be discarded even though no errors had
            been detected to prevent their being transmitted.
            One possible reason for discarding such a packet
            could be to free up buffer space.";
            type uint32;
          }
          leaf DiscardPacketsReceived {
            config false;
            description
            "The total number of inbound packets which were
            chosen to be discarded even though no errors had
            been detected to  prevent their being delivered.
            One possible reason for discarding such a packet
            could be to free up buffer space.";
            type uint32;
          }
          leaf MulticastPacketsSent {
            config false;
            description
            "The total number of packets that higher-level
            protocols requested for transmission and which were
            addressed to a multicast address at this layer,
            including those that were discarded or not sent.";
            type uint64;
          }
          leaf MulticastPacketsReceived {
            config false;
            description
            "The total number of received packets, delivered by
            this layer to a higher layer, which were addressed
            to a multicast address at this layer.";
            type uint64;
          }
          leaf BroadcastPacketsSent {
            config false;
            description
            "Note that IPv6 does not define broadcast addresses,
            so IPv6 packets will never cause this counter to
            increment.";
            type uint64;
          }
          leaf BroadcastPacketsReceived {
            config false;
            description
            "Note that IPv6 does not define broadcast addresses,
            so IPv6 packets will never cause this counter to
            increment.";
            type uint64;
          }
          leaf UnknownProtoPacketsReceived {
            config false;
            description
            "The total number of packets received via the
            interface which were discarded because of an
            unknown or unsupported  protocol.";
            type uint32;
          }
        }
        list TWAMPReflector {
          key "Port";
          unique "Alias";
          config true;
          description
          "This object contains parameters associated with the
          configuration that permits this interface to be used
          as Two-Way Active Measurement Protocol (TWAMP)
          reflector as defined in {{bibref|TR-390}}.";
          leaf Enable {
            config true;
            description
            "Enables or disables the TWAMP reflector.";
            type boolean;
          }
          leaf Status {
            config false;
            description
            "The current operational state of the TWAMP
            reflector.";
            type enumeration {
              enum "Disabled";
              enum "Active";
              enum "Error";
            }
          }
          leaf Alias {
            config true;
            description
            "{{datatype|expand}}";
            type Alias;
          }
          leaf Port {
            config true;
            description
            "The port used to listen for the TWAMP test packets.";
            type uint32 {
              range "min..65535";
            }
          }
          leaf MaximumTTL {
            config true;
            description
            "The maximum TTL of a received packet that this
            TWAMP reflector will reflect to the TWAMP
            controller.";
            type uint32 {
              range "1..255";
            }
            default "1";
          }
          leaf-list IPAllowedList {
            config true;
            description
            "* 2001:edff:fe6a:f76::/64 represents the IPv6
            addresses from 2001:edff:fe6a:f76:0:0:0:0 to
            2001:edff:fe6a:f76:ffff:ffff:ffff:ffff.";
            type string;
          }
          leaf-list PortAllowedList {
            config true;
            description
            "For example, an entry with the value: '2-40'
            accepts test packets from any allowed source IP
            addresses with a source port between 2 and 40
            inclusive.  An entry of '3' accepts test packets
            from allow source IP addresses with a port of 3.";
            type string;
          }
        }
        list IPv6Address {
          key "IPAddress";
          unique "Alias";
          config true;
          description
          "This object is based on ''ipAddressTable'' from
          {{bibref|RFC4293}}.";
          leaf Enable {
            config true;
            description
            "Enables or disables this {{object}} entry.";
            type boolean;
            default "false";
          }
          leaf Status {
            config false;
            description
            "The {{enum|Error}} value MAY be used by the CPE to
            indicate a locally defined error condition.";
            type enumeration {
              enum "Disabled";
              enum "Enabled";
              enum "Error_Misconfigured";
              enum "Error";
            }
            default "Disabled";
          }
          leaf IPAddressStatus {
            config false;
            description
            "This parameter is based on ''ipAddressStatus'' and
            ''ipAddressStatusTC'' from {{bibref|RFC4293}}.";
            type enumeration {
              enum "Preferred" {
                description
                "Valid address that can appear as the
                destination or source address of a packet.";
              }
              enum "Deprecated" {
                description
                "Valid but deprecated address that is not
                intended to be used as a source address.";
              }
              enum "Invalid" {
                description
                "Invalid address that is not intended to appear
                as the destination or source address of a
                packet.";
              }
              enum "Inaccessible" {
                description
                "Valid address that is not accessible because
                the interface to which it is assigned is not
                operational.";
              }
              enum "Unknown" {
                description
                "Address status cannot be determined for some
                reason.";
              }
              enum "Tentative" {
                description
                "The uniqueness of the address on the link is
                being verified.";
              }
              enum "Duplicate" {
                description
                "Invalid address that has been determined to be
                non-unique on the link.";
              }
              enum "Optimistic" {
                description
                "Valid address that is available for use,
                subject to restrictions, while its uniqueness
                on a link is being verified.";
              }
            }
            default "Invalid";
          }
          leaf Alias {
            config true;
            description
            "This parameter can only be modified if
            {{param|Origin}} is {{enum|Static|Origin}}.";
            type Alias;
          }
          leaf IPAddress {
            config true;
            description
            "This parameter is based on ''ipAddressAddr'' from
            {{bibref|RFC4293}}.";
            type inet:ipv6-address;
          }
          leaf Origin {
            config false;
            description
            "This parameter is based on ''ipOrigin'' from
            {{bibref|RFC4293}}.";
            type enumeration {
              enum "AutoConfigured" {
                description
                "Automatically generated.  For example, a
                link-local address as specified by SLAAC
                {{bibref|RFC4862|Section 5.3}}, a global
                address as specified by SLAAC
                {{bibref|RFC4862|Section 5.5}}, or generated
                via CPE logic (e.g.  from delegated prefix as
                specified by {{bibref|RFC3633}}), or from ULA
                /48 prefix as specified by {{bibref|RFC4193}}.";
              }
              enum "DHCPv6" {
                description
                "Assigned by DHCPv6 {{bibref|RFC3315}}.";
              }
              enum "IKEv2" {
                description
                "Assigned by IKEv2 {{bibref|RFC5996}}.";
              }
              enum "MAP" {
                description
                "Assigned by MAP {{bibref|RFC7597}}, i.e.  is
                this interface's ''MAP IPv6 address''";
              }
              enum "WellKnown" {
                description
                "Specified by a standards organization, e.g.
                the ''::1'' loopback address, which is defined
                in {{bibref|RFC4291}}.";
              }
              enum "Static" {
                description
                "For example, present in the factory default
                configuration (but not {{enum|WellKnown}}),
                created by the ACS, or created by some other
                management entity (e.g.  via a GUI).";
              }
            }
            default "Static";
          }
          leaf Prefix {
            config true;
            description
            "This parameter is based on ''ipAddressPrefix'' from
            {{bibref|RFC4293}}.";
            type string;
          }
          leaf PreferredLifetime {
            config true;
            description
            "This parameter can only be modified if the
            {{param|Origin}} is {{enum|Static|Origin}}.";
            type yang:date-and-time;
            default "9999-12-31T23:59:59Z";
          }
          leaf ValidLifetime {
            config true;
            description
            "This parameter can only be modified if the
            {{param|Origin}} is {{enum|Static|Origin}}.";
            type yang:date-and-time;
            default "9999-12-31T23:59:59Z";
          }
          leaf Anycast {
            config true;
            description
            "This parameter is based on ''ipAddressType'' from
            {{bibref|RFC4293}}.";
            type boolean;
            default "false";
          }
        }
        list IPv6Prefix {
          key "Prefix";
          unique "Alias";
          config true;
          description
          "This object is based on ''ipAddressPrefixTable'' from
          {{bibref|RFC4293}}.";
          leaf Enable {
            config true;
            description
            "Enables or disables this {{object}} entry.";
            type boolean;
            default "false";
          }
          leaf Status {
            config false;
            description
            "The {{enum|Error}} value MAY be used by the CPE to
            indicate a locally defined error condition.";
            type enumeration {
              enum "Disabled";
              enum "Enabled";
              enum "Error";
            }
            default "Disabled";
          }
          leaf PrefixStatus {
            config false;
            description
            "This parameter is based on ''ipAddressStatus'' and
            ''ipAddressStatusTC'' from {{bibref|RFC4293}}.";
            type enumeration {
              enum "Preferred" {
                description
                "Valid prefix.";
              }
              enum "Deprecated" {
                description
                "Valid but deprecated prefix.";
              }
              enum "Invalid" {
                description
                "Invalid prefix.";
              }
              enum "Inaccessible" {
                description
                "Valid prefix that is not accessible because the
                interface to which it is assigned is not
                operational.";
              }
              enum "Unknown" {
                description
                "Prefix status cannot be determined for some
                reason.";
              }
            }
            default "Invalid";
          }
          leaf Alias {
            config true;
            description
            "This parameter can only be modified if
            {{param|Origin}} is {{enum|Static|Origin}}.";
            type Alias;
          }
          leaf Prefix {
            config true;
            description
            "This parameter is based on
            ''ipAddressPrefixPrefix'' from {{bibref|RFC4293}}.";
            type inet:ipv6-prefix;
          }
          leaf Origin {
            config false;
            description
            "This parameter is based on ''ipAddressOrigin'' from
            {{bibref|RFC4293}}.";
            type enumeration {
              enum "AutoConfigured" {
                description
                "Generated via internal CPE logic (e.g.  the ULA
                /48 prefix) or derived from an internal prefix
                that is not modeled in any {{object}} table.";
              }
              enum "PrefixDelegation" {
                description
                "Delegated via DHCPv6 {{bibref|RFC3633}} or some
                other protocol, e.g.  IPv6rd
                {{bibref|RFC5969}}.  Also see
                {{param|StaticType}}.";
              }
              enum "RouterAdvertisement" {
                description
                "Discovered via router advertisement
                {{bibref|RFC4861}} Prefix Information Option.";
              }
              enum "WellKnown" {
                description
                "Specified by a standards organization, e.g.
                ''fe80::/10'' for link-local addresses, or
                ''::1/128'' for the loopback address, both of
                which are defined in {{bibref|RFC4291}}.";
              }
              enum "Static" {
                description
                "Created by the ACS, by some other management
                entity (e.g.  via a GUI), or present in the
                factory default configuration (but not
                {{enum|WellKnown}}).  Unrelated to any shorter
                length prefix that might exist on the CPE.
                Also see {{param|StaticType}}.  Can be used for
                RA (Prefix Information), DHCPv6 address
                assignment (IA_NA) or DHCPv6 prefix delegation
                (IA_PD).";
              }
              enum "Child" {
                description
                "Derived from an associated
                {{enum|AutoConfigured}} or
                {{enum|PrefixDelegation}} parent prefix.  Also
                see {{param|StaticType}},
                {{param|ParentPrefix}} and
                {{param|ChildPrefixBits}}.  Can be used for RA
                (Prefix Information), DHCPv6 address assignment
                (IA_NA) or DHCPv6 prefix delegation (IA_PD).";
              }
            }
            default "Static";
          }
          leaf StaticType {
            config true;
            description
            "The prefix {{param}} can only be modified if
            {{param|Origin}} is {{enum|Static|Origin}}.";
            type enumeration {
              enum "Static" {
                description
                "Prefix is a \"normal\" {{enum|Static|Origin}}
                prefix.";
              }
              enum "Inapplicable" {
                description
                "Prefix is not {{enum|Static|Origin}}, so this
                parameter does not apply.";
              }
              enum "PrefixDelegation" {
                description
                "Prefix will be populated when a
                {{enum|PrefixDelegation|Origin}} prefix needs
                to be created.";
              }
              enum "Child" {
                description
                "Prefix will be populated when a
                {{enum|Child|Origin}} prefix needs to be
                created.  In this case, the ACS needs also to
                set {{param|ParentPrefix}} and might want to
                set {{param|ChildPrefixBits}} (if parent prefix
                is not set, or goes away, then the child prefix
                will become operationally disabled).";
              }
            }
            default "Static";
          }
          leaf ParentPrefix {
            config true;
            description
            "This parameter can only be modified if
            {{param|Origin}} is {{enum|Static|Origin}} (which
            makes sense only for a prefix whose
            {{param|StaticType}} is already or will be changed
            to {{enum|Child|StaticType}}).";
            type string;
          }
          leaf ChildPrefixBits {
            config true;
            description
            "This parameter can only be modified if
            {{param|Origin}} is {{enum|Static|Origin}}.";
            type inet:ipv6-prefix;
          }
          leaf OnLink {
            config true;
            description
            "This parameter is based on
            ''ipAddressPrefixOnLinkFlag'' from
            {{bibref|RFC4293}}.";
            type boolean;
            default "false";
          }
          leaf Autonomous {
            config true;
            description
            "This parameter is based on
            ''ipAddressPrefixAutonomousFlag'' from
            {{bibref|RFC4293}}.";
            type boolean;
            default "false";
          }
          leaf PreferredLifetime {
            config true;
            description
            "This parameter can only be modified if
            {{param|Origin}} is {{enum|Static|Origin}}.";
            type yang:date-and-time;
            default "9999-12-31T23:59:59Z";
          }
          leaf ValidLifetime {
            config true;
            description
            "This parameter can only be modified if
            {{param|Origin}} is {{enum|Static|Origin}}.";
            type yang:date-and-time;
            default "9999-12-31T23:59:59Z";
          }
        }
      }
      list ActivePort {
        key "LocalIPAddress LocalPort RemoteIPAddress RemotePort";
        config false;
        description
        "This table lists the ports on which TCP connections are
        listening or established.";
        leaf LocalIPAddress {
          config false;
          description
          "Connection local IP address.";
          type inet:ip-address;
        }
        leaf LocalPort {
          config false;
          description
          "Connection local port.";
          type uint32 {
            range "0..65535";
          }
        }
        leaf RemoteIPAddress {
          config false;
          description
          "This will be {{null}} for listening connections (only
          connections in {{enum|ESTABLISHED|Status}} state have
          remote addresses).";
          type inet:ip-address;
        }
        leaf RemotePort {
          config false;
          description
          "This will be {{null}} for listening connections (only
          connections in {{enum|ESTABLISHED|Status}} state have
          remote addresses).";
          type uint32 {
            range "0..65535";
          }
        }
        leaf Status {
          config false;
          description
          "Current operational status of the connection.
          {{enum}}";
          type enumeration {
            enum "LISTEN";
            enum "ESTABLISHED";
          }
        }
      }
      container Diagnostics {
        description
        "The IP Diagnostics object.";
        leaf IPv4PingSupported {
          config false;
          description
          "Indicates that Ping over IPv4 is supported.";
          type boolean;
        }
        leaf IPv6PingSupported {
          config false;
          description
          "Indicates that Ping over IPv6 is supported.";
          type boolean;
        }
        leaf IPv4TraceRouteSupported {
          config false;
          description
          "Indicates that TraceRoute over IPv4 is supported.";
          type boolean;
        }
        leaf IPv6TraceRouteSupported {
          config false;
          description
          "Indicates that TraceRoute over IPv6 is supported.";
          type boolean;
        }
        leaf IPv4DownloadDiagnosticsSupported {
          config false;
          description
          "Indicates that Download Diagnostics over IPv4 is
          supported.";
          type boolean;
        }
        leaf IPv6DownloadDiagnosticsSupported {
          config false;
          description
          "Indicates that Download Diagnostics over IPv6 is
          supported.";
          type boolean;
        }
        leaf IPv4UploadDiagnosticsSupported {
          config false;
          description
          "Indicates that Upload Diagnostics over IPv4 is
          supported.";
          type boolean;
        }
        leaf IPv6UploadDiagnosticsSupported {
          config false;
          description
          "Indicates that Upload Diagnostics over IPv6 is
          supported.";
          type boolean;
        }
        leaf IPv4UDPEchoDiagnosticsSupported {
          config false;
          description
          "Indicates that UDPEcho Diagnostics over IPv4 is
          supported.";
          type boolean;
        }
        leaf IPv6UDPEchoDiagnosticsSupported {
          config false;
          description
          "Indicates that UDPEcho Diagnostics over IPv6 is
          supported.";
          type boolean;
        }
        leaf IPv4ServerSelectionDiagnosticsSupported {
          config false;
          description
          "Indicates that ServerSelection Diagnostics over IPv4
          is supported.";
          type boolean;
        }
        leaf IPv6ServerSelectionDiagnosticsSupported {
          config false;
          description
          "Indicates that ServerSelection Diagnostics over IPv6
          is supported.";
          type boolean;
        }
        container IPPing {
          description
          "This object provides access to an IP-layer ping test.";
          leaf DiagnosticsState {
            config true;
            description
            "{{datatype|expand}}";
            type DiagnosticsState;
          }
          leaf Interface {
            config true;
            description
            "If {{empty}} is specified, the CPE MUST use the
            interface as directed by its bridging or routing
            policy (''Forwarding'' table entries) to determine
            the appropriate interface.";
            type string {
              length "0..256";
            }
          }
          leaf ProtocolVersion {
            config true;
            description
            "Indicates the IP protocol to be used.";
            type enumeration {
              enum "Any" {
                description
                "Use either IPv4 or IPv6 depending on the system
                preference";
              }
              enum "IPv4" {
                description
                "Use IPv4 for the Ping requests";
              }
              enum "IPv6" {
                description
                "Use IPv6 for the Ping requests";
              }
            }
          }
          leaf Host {
            config true;
            description
            "In the case where {{param}} is specified by name,
            and the name resolves to more than one address, it
            is up to the device implementation to choose which
            address to use.";
            type string {
              length "0..256";
            }
          }
          leaf NumberOfRepetitions {
            config true;
            description
            "Number of repetitions of the ping test to perform
            before reporting the results.";
            type uint32 {
              range "1..max";
            }
          }
          leaf Timeout {
            config true;
            description
            "Timeout in {{units}} for the ping test.";
            type uint32 {
              range "1..max";
            }
          }
          leaf DataBlockSize {
            config true;
            description
            "Size of the data block in bytes to be sent for each
            ping.";
            type uint32 {
              range "1..65535";
            }
          }
          leaf DSCP {
            config true;
            description
            "DiffServ codepoint to be used for the test packets.
            By default the CPE SHOULD set this value to  zero.";
            type uint32 {
              range "0..63";
            }
          }
          leaf IPAddressUsed {
            config false;
            description
            "Indicates which IP address was used to send the
            Ping request.  The parameter is only valid if the
            {{param|DiagnosticsState}} is
            {{enum|Complete|DiagnosticsState}}.";
            type inet:ip-address;
          }
          leaf SuccessCount {
            config false;
            description
            "Result parameter indicating the number of
            successful pings (those in which a successful
            response was received  prior to the timeout) in the
            most recent ping test.";
            type uint32;
          }
          leaf FailureCount {
            config false;
            description
            "Result parameter indicating the number of failed
            pings in the most recent ping test.";
            type uint32;
          }
          leaf AverageResponseTime {
            config false;
            description
            "Result parameter indicating the average response
            time in {{units}} over all repetitions with
            successful  responses of the most recent ping test.
            If there were no successful responses, this value
            MUST be zero.";
            type uint32;
          }
          leaf MinimumResponseTime {
            config false;
            description
            "Result parameter indicating the minimum response
            time in {{units}} over all repetitions with
            successful  responses of the most recent ping test.
            If there were no successful responses, this value
            MUST be zero.";
            type uint32;
          }
          leaf MaximumResponseTime {
            config false;
            description
            "Result parameter indicating the maximum response
            time in {{units}} over all repetitions with
            successful  responses of the most recent ping test.
            If there were no successful responses, this value
            MUST be zero.";
            type uint32;
          }
          leaf AverageResponseTimeDetailed {
            config false;
            description
            "Result parameter indicating the average response
            time in {{units}} over all repetitions with
            successful responses of the most recent ping test.
            If there were no successful responses, this value
            MUST be zero.";
            type uint32;
          }
          leaf MinimumResponseTimeDetailed {
            config false;
            description
            "Result parameter indicating the minimum response
            time in {{units}} over all repetitions with
            successful responses of the most recent ping test.
            If there were no successful responses, this value
            MUST be zero.";
            type uint32;
          }
          leaf MaximumResponseTimeDetailed {
            config false;
            description
            "Result parameter indicating the maximum response
            time in {{units}} over all repetitions with
            successful responses of the most recent ping test.
            If there were no successful responses, this value
            MUST be zero.";
            type uint32;
          }
        }
        container TraceRoute {
          description
          "This object defines access to an IP-layer trace-route
          test for the specified IP interface.";
          leaf DiagnosticsState {
            config true;
            description
            "{{datatype|expand}}";
            type DiagnosticsState;
          }
          leaf Interface {
            config true;
            description
            "If {{empty}} is specified, the CPE MUST use the
            interface as directed by its bridging or routing
            policy (''Forwarding'' table entries) to determine
            the appropriate interface.";
            type string {
              length "0..256";
            }
          }
          leaf ProtocolVersion {
            config true;
            description
            "Indicates the IP protocol to be used.";
            type enumeration {
              enum "Any" {
                description
                "Use either IPv4 or IPv6 depending on the system
                preference";
              }
              enum "IPv4" {
                description
                "Use IPv4 for the TraceRoute";
              }
              enum "IPv6" {
                description
                "Use IPv6 for the TraceRoute";
              }
            }
          }
          leaf Host {
            config true;
            description
            "In the case where {{param}} is specified by name,
            and the name resolves to more than one address, it
            is up to the device implementation to choose which
            address to use.";
            type string {
              length "0..256";
            }
          }
          leaf NumberOfTries {
            config true;
            description
            "Number of tries per hop.  Set prior to running
            Diagnostic.  By default, the CPE SHOULD set this
            value to  3.";
            type uint32 {
              range "1..3";
            }
          }
          leaf Timeout {
            config true;
            description
            "Timeout in {{units}} for each hop of the trace
            route test.  By default the CPE SHOULD set this
            value to 5000.";
            type uint32 {
              range "1..max";
            }
          }
          leaf DataBlockSize {
            config true;
            description
            "Size of the data block in bytes to be sent for each
            trace route.  By default, the CPE SHOULD set this
            value to  38.";
            type uint32 {
              range "1..65535";
            }
          }
          leaf DSCP {
            config true;
            description
            "DiffServ codepoint to be used for the test packets.
            By default the CPE SHOULD set this value to  0.";
            type uint32 {
              range "0..63";
            }
          }
          leaf MaxHopCount {
            config true;
            description
            "The maximum number of hop used in outgoing probe
            packets (max TTL).  By default the CPE SHOULD set
            this value to  30.";
            type uint32 {
              range "1..64";
            }
          }
          leaf IPAddressUsed {
            config false;
            description
            "Indicates which IP address was used for TraceRoute.
            The parameter is only valid if the
            {{param|DiagnosticsState}} is
            {{enum|Complete|DiagnosticsState}}.";
            type inet:ip-address;
          }
          leaf ResponseTime {
            config false;
            description
            "Result parameter indicating the response time in
            {{units}} the most recent trace route test.  If a
            route  could not be determined, this value MUST be
            zero.";
            type uint32;
          }
          leaf RouteHopsNumberOfEntries {
            config false;
            description
            "{{numentries}}";
            type uint32;
          }
          list RouteHops {
            key "_id";
            leaf "_id" {
              type "uint32";
            }
            config false;
            description
            "Contains the array of hop results returned.  If a
            route could not be determined, this array will be
            empty";
            leaf Host {
              config false;
              description
              "Result parameter indicating the Host Name if DNS
              is able to resolve or IP Address of a hop along
              the discovered  route.";
              type string {
                length "0..256";
              }
            }
            leaf HostAddress {
              config false;
              description
              "If this parameter is not {{empty}} it will
              contain the last IP address of the host returned
              for this hop and the  {{param|Host}} will contain
              the Host Name returned from the reverse DNS
              query.";
              type string;
            }
            leaf ErrorCode {
              config false;
              description
              "Contains the error code returned for this hop.
              This code is directly from the ICMP CODE field.";
              type uint32;
            }
            leaf-list RTTimes {
              config false;
              description
              "The number of list entries is determined by the
              value of {{param|#.NumberOfTries}}.";
              type uint32;
            }
          }
        }
        container DownloadDiagnostics {
          description
          "Files received in the DownloadDiagnostics do not
          require file storage on the CPE device.";
          leaf DiagnosticsState {
            config true;
            description
            "While the test is in progress, setting this
            parameter to {{enum|Requested}} (and possibly
            modifying other writable parameters in this object)
            MUST result in the test being terminated and then
            restarted using the current values of the test
            parameters.";
            type enumeration {
              enum "None";
              enum "Requested";
              enum "Completed";
              enum "Error_CannotResolveHostName";
              enum "Error_NoRouteToHost";
              enum "Error_InitConnectionFailed";
              enum "Error_NoResponse";
              enum "Error_TransferFailed";
              enum "Error_PasswordRequestFailed";
              enum "Error_LoginFailed";
              enum "Error_NoTransferMode";
              enum "Error_NoPASV";
              enum "Error_IncorrectSize";
              enum "Error_Timeout";
              enum "Error_Internal";
              enum "Error_Other";
            }
          }
          leaf Interface {
            config true;
            description
            "If {{empty}} is specified, the CPE MUST use the
            interface as directed by its routing policy
            (''Forwarding'' table entries) to determine the
            appropriate interface.";
            type string {
              length "0..256";
            }
          }
          leaf DownloadURL {
            config true;
            description
            "Note: For time based tests
            ({{param|TimeBasedTestDuration}} > 0) the ACS MAY
            add a hint to duration of the test to the URL.  See
            {{bibref|TR-143a1|Section 4.3}} for more details.";
            type string {
              length "0..256";
            }
          }
          leaf-list DownloadTransports {
            config false;
            description
            "Supported ''DownloadDiagnostics'' transport
            protocols for a CPE device.";
            type enumeration {
              enum "HTTP";
              enum "FTP";
            }
          }
          leaf DownloadDiagnosticMaxConnections {
            config false;
            description
            "Indicates the maximum number of connections that
            are supported by Download Diagnostics.";
            type uint32 {
              range "1..max";
            }
          }
          leaf DownloadDiagnosticsMaxIncrementalResult {
            config false;
            description
            "The maximum number of rows in
            {{object|IncrementalResult}} that the CPE will
            store.";
            type uint32 {
              range "1..max";
            }
          }
          leaf DSCP {
            config true;
            description
            "The default value SHOULD be zero.";
            type uint32 {
              range "0..63";
            }
          }
          leaf EthernetPriority {
            config true;
            description
            "The default value SHOULD be zero.";
            type uint32 {
              range "0..7";
            }
          }
          leaf TimeBasedTestDuration {
            config true;
            description
            "Controls time based testing
            {{bibref|TR-143a1|Section 4.3}}. When {{param}} >
            0, {{param}} is the duration in {{units}} of a time
            based test.  If {{param}} is 0, the test is not
            based on time, but on the size of the file to be
            downloaded.  The default value SHOULD be 0.";
            type uint32 {
              range "0..999";
            }
          }
          leaf TimeBasedTestMeasurementInterval {
            config true;
            description
            "For example if {{param|TimeBasedTestDuration}} is
            90 seconds and {{param}} is 10 {{units}}, there
            will be 9 results in {{object|IncrementalResult}},
            each with a 10 {{units}} duration.";
            type uint32 {
              range "0..999";
            }
          }
          leaf TimeBasedTestMeasurementOffset {
            config true;
            description
            "This {{param}} is in {{units}}.  The default value
            SHOULD be 0.";
            type uint32 {
              range "0..255";
            }
          }
          leaf ProtocolVersion {
            config true;
            description
            "Indicates the IP protocol version to be used.  The
            default value SHOULD be {{enum|Any}}.";
            type enumeration {
              enum "Any" {
                description
                "Use either IPv4 or IPv6 depending on the system
                preference.";
              }
              enum "IPv4" {
                description
                "Use IPv4 for the requests";
              }
              enum "IPv6" {
                description
                "Use IPv6 for the requests.";
              }
            }
          }
          leaf NumberOfConnections {
            config true;
            description
            "The number of connections to be used in the test.
            The default value SHOULD be 1.  {{param}} MUST NOT
            be set to a value greater than
            {{param|DownloadDiagnosticMaxConnections}}.";
            type uint32 {
              range "1..max";
            }
          }
          leaf IPAddressUsed {
            config false;
            description
            "Indicates which IP address was used to send the
            request.";
            type inet:ip-address;
          }
          leaf ROMTime {
            config false;
            description
            "If multiple connections are used, then {{param}} is
            set to the earliest {{param}} across all
            connections.";
            type yang:date-and-time;
          }
          leaf BOMTime {
            config false;
            description
            "If multiple connections are used, then {{param}} is
            set to the earliest {{param}} across all
            connections.";
            type yang:date-and-time;
          }
          leaf EOMTime {
            config false;
            description
            "If multiple connections are used, then {{param}} is
            set to the latest {{param}} across all connections.";
            type yang:date-and-time;
          }
          leaf TestBytesReceived {
            config false;
            description
            "The number of {{units}} received during the
            FTP/HTTP transaction including FTP/HTTP headers,
            between {{param|BOMTime}} and {{param|EOMTime}}
            across all connections.";
            type uint32;
          }
          leaf TotalBytesReceived {
            config false;
            description
            "The total number of {{units}} (at the IP layer)
            received on the Interface between {{param|BOMTime}}
            and {{param|EOMTime}}.  This MAY be calculated by
            sampling Stats.bytesReceived on the
            {{param|Interface}} object at {{param|BOMTime}} and
            at {{param|EOMTime}} and subtracting.";
            type uint32;
          }
          leaf TotalBytesSent {
            config false;
            description
            "The total number of {{units}} (at the IP layer)
            sent on the Interface between {{param|BOMTime}} and
            {{param|EOMTime}}.  This MAY be calculated by
            sampling Stats.bytesSent on the {{param|Interface}}
            object at {{param|BOMTime}} and at
            {{param|EOMTime}} and subtracting.";
            type uint32;
          }
          leaf TestBytesReceivedUnderFullLoading {
            config false;
            description
            "The number of {{units}} of the test file received
            between the latest
            {{param|PerConnectionResult.{i}.BOMTime}} and the
            earliest {{param|PerConnectionResult.{i}.EOMTime}}
            across all connections.";
            type uint32;
          }
          leaf TotalBytesReceivedUnderFullLoading {
            config false;
            description
            "The total number of {{units}} (at the IP layer)
            received in between the latest
            {{param|PerConnectionResult.{i}.BOMTime}} and the
            earliest {{param|PerConnectionResult.{i}.EOMTime}}.
            This MAY be calculated by sampling
            Stats.bytesReceived on the {{param|Interface}}
            object at the latest
            {{param|PerConnectionResult.{i}.BOMTime}} and at
            the earliest
            {{param|PerConnectionResult.{i}.EOMTime}} and
            subtracting.";
            type uint32;
          }
          leaf TotalBytesSentUnderFullLoading {
            config false;
            description
            "The total number of {{units}} (at the IP layer)
            sent between the latest
            {{param|PerConnectionResult.{i}.BOMTime}} and the
            earliest {{param|PerConnectionResult.{i}.EOMTime}}.
            This MAY be calculated by sampling Stats.bytesSent
            on the {{param|Interface}} object at the latest
            {{param|PerConnectionResult.{i}.BOMTime}} and at
            the earliest
            {{param|PerConnectionResult.{i}.EOMTime}} and
            subtracting.";
            type uint32;
          }
          leaf PeriodOfFullLoading {
            config false;
            description
            "The period of time in {{units}} between the latest
            {{param|PerConnectionResult.{i}.BOMTime}} and the
            earliest {{param|PerConnectionResult.{i}.EOMTime}}
            of the test.";
            type uint32;
          }
          leaf TCPOpenRequestTime {
            config false;
            description
            "If multiple connections are used, then {{param}} is
            set to the latest {{param}} across all connections.";
            type yang:date-and-time;
          }
          leaf TCPOpenResponseTime {
            config false;
            description
            "If multiple connections are used, then {{param}} is
            set to the latest {{param}} across all connections.";
            type yang:date-and-time;
          }
          leaf PerConnectionResultNumberOfEntries {
            config false;
            description
            "{{numentries}}";
            type uint32;
          }
          leaf EnablePerConnectionResults {
            config true;
            description
            "The results must be returned in the
            {{object|PerConnectionResult}} table for every
            connection when set to {{true}}. The default value
            SHOULD be {{false}}.";
            type boolean;
          }
          leaf IncrementalResultNumberOfEntries {
            config false;
            description
            "{{numentries}}";
            type uint32;
          }
          list PerConnectionResult {
            key "_id";
            leaf "_id" {
              type "uint32";
            }
            config false;
            description
            "Results for individual connections.  This table is
            only populated when
            {{param|#.EnablePerConnectionResults}} is {{true}}.
            A new object is created for each connection
            specified in {{param|#.NumberOfConnections}}.
            Instance numbers MUST start at 1 and sequentially
            increment as new instances are created.  All
            instances are removed when
            {{param|#.DiagnosticsState}} is set to
            {{enum|Requested|#.DiagnosticsState}} or
            {{enum|None|#.DiagnosticsState}}.";
            leaf ROMTime {
              config false;
              description
              "* For FTP this is the time at which the client
              sends the RTRV command.";
              type yang:date-and-time;
            }
            leaf BOMTime {
              config false;
              description
              "* For FTP this is the time at which the client
              receives the first data packet on the data
              connection.";
              type yang:date-and-time;
            }
            leaf EOMTime {
              config false;
              description
              "* For FTP this is the time at which the client
              receives the last packet on the data connection.";
              type yang:date-and-time;
            }
            leaf TestBytesReceived {
              config false;
              description
              "The number of {{units}} of the test file received
              during the FTP/HTTP transaction including
              FTP/HTTP headers, between {{param|BOMTime}} and
              {{param|EOMTime}}.";
              type uint32;
            }
            leaf TotalBytesReceived {
              config false;
              description
              "The total number of {{units}} (at the IP layer)
              received on the Interface between
              {{param|BOMTime}} and {{param|EOMTime}}.  This
              MAY be calculated by sampling Stats.bytesReceived
              on the {{param|#.Interface}} object at
              {{param|BOMTime}} and at {{param|EOMTime}} and
              subtracting.";
              type uint32;
            }
            leaf TotalBytesSent {
              config false;
              description
              "The total number of {{units}} (at the IP layer)
              sent on the Interface between {{param|BOMTime}}
              and {{param|EOMTime}}.  This MAY be calculated by
              sampling Stats.bytesSent on the
              {{param|#.Interface}} object at {{param|BOMTime}}
              and at {{param|EOMTime}} and subtracting.";
              type uint32;
            }
            leaf TCPOpenRequestTime {
              config false;
              description
              "* For FTP this is the time at which the TCP
              socket open (SYN) was sent for the data
              connection.";
              type yang:date-and-time;
            }
            leaf TCPOpenResponseTime {
              config false;
              description
              "* For FTP this is the time at which the TCP ACK
              to the socket opening the data connection was
              received.";
              type yang:date-and-time;
            }
          }
          list IncrementalResult {
            key "_id";
            leaf "_id" {
              type "uint32";
            }
            config false;
            description
            "Results for time segmented tests (tests where
            {{param|#.TimeBasedTestDuration}} > 0 and
            {{param|#.TimeBasedTestMeasurementInterval}} > 0).
            This data is totaled across all connections in the
            test.  A new object is created every
            {{param|#.TimeBasedTestMeasurementInterval}} after
            that interval has completed.  Instance numbers MUST
            start at 1 and sequentially increment as new
            instances are created.  All instances are removed
            when {{param|#.DiagnosticsState}} is set to
            {{enum|Requested|#.DiagnosticsState}} or
            {{enum|None|#.DiagnosticsState}}.";
            leaf TestBytesReceived {
              config false;
              description
              "Change in the value of
              {{param|#.TestBytesReceivedUnderFullLoading}}
              between {{param|StartTime}} and
              {{param|EndTime}}.";
              type uint32;
            }
            leaf TotalBytesReceived {
              config false;
              description
              "The total number of {{units}} (at the IP layer)
              received on the Interface between
              {{param|StartTime}} and {{param|EndTime}}.  This
              MAY be calculated by sampling Stats.bytesReceived
              on the {{param|#.Interface}} object at
              {{param|StartTime}} and at {{param|EndTime}} and
              subtracting.";
              type uint32;
            }
            leaf TotalBytesSent {
              config false;
              description
              "The total number of {{units}} (at the IP layer)
              sent on the Interface between {{param|StartTime}}
              and {{param|EndTime}}.  This MAY be calculated by
              sampling Stats.bytesSent on the
              {{param|#.Interface}} object at
              {{param|StartTime}} and at {{param|EndTime}} and
              subtracting.";
              type uint32;
            }
            leaf StartTime {
              config false;
              description
              "For example: 2008-04-09T15:01:05.123456Z";
              type yang:date-and-time;
            }
            leaf EndTime {
              config false;
              description
              "For example: 2008-04-09T15:01:05.123456Z";
              type yang:date-and-time;
            }
          }
        }
        container UploadDiagnostics {
          description
          "Files sent by the UploadDiagnostics do not require
          file storage on the CPE device, and MAY be an
          arbitrary stream of bytes.";
          leaf DiagnosticsState {
            config true;
            description
            "While the test is in progress, setting this
            parameter to {{enum|Requested}} (and possibly
            modifying other writable parameters in this object)
            MUST result in the test being terminated and then
            restarted using the current values of the test
            parameters.";
            type enumeration {
              enum "None";
              enum "Requested";
              enum "Completed";
              enum "Error_CannotResolveHostName";
              enum "Error_NoRouteToHost";
              enum "Error_InitConnectionFailed";
              enum "Error_NoResponse";
              enum "Error_PasswordRequestFailed";
              enum "Error_LoginFailed";
              enum "Error_NoTransferMode";
              enum "Error_NoPASV";
              enum "Error_NoCWD";
              enum "Error_NoSTOR";
              enum "Error_NoTransferComplete";
              enum "Error_Timeout";
              enum "Error_Internal";
              enum "Error_Other";
            }
          }
          leaf Interface {
            config true;
            description
            "If {{empty}} is specified, the CPE MUST use the
            interface as directed by its routing policy
            (''Forwarding'' table entries) to determine the
            appropriate interface.";
            type string {
              length "0..256";
            }
          }
          leaf UploadURL {
            config true;
            description
            "* When using HTTP transport the HTTP Authentication
            MUST NOT be used.";
            type string {
              length "0..256";
            }
          }
          leaf-list UploadTransports {
            config false;
            description
            "Supported ''UploadDiagnostics'' transport protocols
            for a CPE device.";
            type enumeration {
              enum "HTTP";
              enum "FTP";
            }
          }
          leaf UploadDiagnosticsMaxConnections {
            config false;
            description
            "Indicates the maximum number of connections that
            are supported by Upload Diagnostics.";
            type uint32 {
              range "1..max";
            }
          }
          leaf UploadDiagnosticsMaxIncrementalResult {
            config false;
            description
            "The maximum number of rows in
            {{object|IncrementalResult}} that the CPE will
            store.";
            type uint32 {
              range "1..max";
            }
          }
          leaf DSCP {
            config true;
            description
            "The default value SHOULD be zero.";
            type uint32 {
              range "0..63";
            }
          }
          leaf EthernetPriority {
            config true;
            description
            "The default value SHOULD be zero.";
            type uint32 {
              range "0..7";
            }
          }
          leaf TestFileLength {
            config true;
            description
            "The CPE MUST insure the appropriate number of bytes
            are sent.";
            type uint32;
          }
          leaf TimeBasedTestDuration {
            config true;
            description
            "Controls time based testing
            {{bibref|TR-143a1|Section 4.3}}. When {{param}} >
            0, {{param}} is the duration in {{units}} of a time
            based test.  If {{param}} is 0, the test is not
            based on time, but on the size of the file to be
            uploaded.  The default value SHOULD be 0.";
            type uint32 {
              range "0..999";
            }
          }
          leaf TimeBasedTestMeasurementInterval {
            config true;
            description
            "For example if {{param|TimeBasedTestDuration}} is
            90 seconds and {{param}} is 10 {{units}}, there
            will be 9 results in {{object|IncrementalResult}},
            each with a 10 {{units}} duration.";
            type uint32 {
              range "0..999";
            }
          }
          leaf TimeBasedTestMeasurementOffset {
            config true;
            description
            "This {{param}} is in {{units}}.  The default value
            SHOULD be 0.";
            type uint32 {
              range "0..255";
            }
          }
          leaf ProtocolVersion {
            config true;
            description
            "Indicates the IP protocol version to be used.  The
            default value SHOULD be {{enum|Any}}.";
            type enumeration {
              enum "Any" {
                description
                "Use either IPv4 or IPv6 depending on the system
                preference.";
              }
              enum "IPv4" {
                description
                "Use IPv4 for the requests";
              }
              enum "IPv6" {
                description
                "Use IPv6 for the requests.";
              }
            }
          }
          leaf NumberOfConnections {
            config true;
            description
            "The number of connections to be used in the test.
            The default value SHOULD be 1.  {{param}} MUST NOT
            be set to a value greater than
            {{param|UploadDiagnosticsMaxConnections}}.";
            type uint32 {
              range "1..max";
            }
          }
          leaf IPAddressUsed {
            config false;
            description
            "Indicates which IP address was used to send the
            request.";
            type inet:ip-address;
          }
          leaf ROMTime {
            config false;
            description
            "If multiple connections are used, then {{param}} is
            set to the earliest {{param}} across all
            connections.";
            type yang:date-and-time;
          }
          leaf BOMTime {
            config false;
            description
            "If multiple connections are used, then {{param}} is
            set to the earliest {{param}} across all
            connections.";
            type yang:date-and-time;
          }
          leaf EOMTime {
            config false;
            description
            "If multiple connections are used, then {{param}} is
            set to the latest {{param}} across all connections.";
            type yang:date-and-time;
          }
          leaf TestBytesSent {
            config false;
            description
            "The number of {{units}} of the test file sent
            during the FTP/HTTP transaction including FTP/HTTP
            headers, between {{param|BOMTime}} and
            {{param|EOMTime}} acrosss all connections.";
            type uint32;
          }
          leaf TotalBytesReceived {
            config false;
            description
            "The total number of {{units}} (at the IP layer)
            received on the Interface between {{param|BOMTime}}
            and {{param|EOMTime}}.  This MAY be calculated by
            sampling Stats.bytesReceived on the
            {{param|Interface}} object at {{param|BOMTime}} and
            at {{param|EOMTime}} and subtracting.";
            type uint32;
          }
          leaf TotalBytesSent {
            config false;
            description
            "The total number of {{units}} (at the IP layer)
            sent on the Interface between {{param|BOMTime}} and
            {{param|EOMTime}}.  This MAY be calculated by
            sampling Stats.bytesSent on the {{param|Interface}}
            object at {{param|BOMTime}} and at
            {{param|EOMTime}} and subtracting.";
            type uint32;
          }
          leaf TestBytesSentUnderFullLoading {
            config false;
            description
            "The number of {{units}} of the test file sent
            between the latest
            {{param|PerConnectionResult.{i}.BOMTime}} and the
            earliest {{param|PerConnectionResult.{i}.EOMTime}}
            across all connections.";
            type uint32;
          }
          leaf TotalBytesReceivedUnderFullLoading {
            config false;
            description
            "The total number of {{units}} (at the IP layer)
            received between the latest
            {{param|PerConnectionResult.{i}.BOMTime}} and the
            earliest {{param|PerConnectionResult.{i}.EOMTime}}
            across all connections in the test.  This MAY be
            calculated by sampling Stats.bytesReceived on the
            {{param|Interface}} object at the latest
            {{param|PerConnectionResult.{i}.BOMTime}} and at
            the earliest
            {{param|PerConnectionResult.{i}.EOMTime}} and
            subtracting.";
            type uint32;
          }
          leaf TotalBytesSentUnderFullLoading {
            config false;
            description
            "The total number of {{units}} (at the IP layer)
            sent between the latest
            {{param|PerConnectionResult.{i}.BOMTime}} and the
            earliest {{param|PerConnectionResult.{i}.EOMTime}}
            across all connections in the test.  This MAY be
            calculated by sampling Stats.bytesSent on the
            {{param|Interface}} object at the latest
            {{param|PerConnectionResult.{i}.BOMTime}} and at
            the earliest
            {{param|PerConnectionResult.{i}.EOMTime}} and
            subtracting.";
            type uint32;
          }
          leaf PeriodOfFullLoading {
            config false;
            description
            "The period of time in {{units}} between the latest
            {{param|PerConnectionResult.{i}.BOMTime}} and the
            earliest {{param|PerConnectionResult.{i}.EOMTime}}
            of the test.";
            type uint32;
          }
          leaf TCPOpenRequestTime {
            config false;
            description
            "If multiple connections are used, then {{param}} is
            set to the latest {{param}} across all connections.";
            type yang:date-and-time;
          }
          leaf TCPOpenResponseTime {
            config false;
            description
            "If multiple connections are used, then {{param}} is
            set to the latest {{param}} across all connections.";
            type yang:date-and-time;
          }
          leaf PerConnectionResultNumberOfEntries {
            config false;
            description
            "{{numentries}}";
            type uint32;
          }
          leaf EnablePerConnectionResults {
            config true;
            description
            "The results must be returned in the
            {{object|PerConnectionResult}} table for every
            connection when set to {{true}}. The default value
            SHOULD be {{false}}.";
            type boolean;
          }
          leaf IncrementalResultNumberOfEntries {
            config false;
            description
            "{{numentries}}";
            type uint32;
          }
          list PerConnectionResult {
            key "_id";
            leaf "_id" {
              type "uint32";
            }
            config false;
            description
            "Results for individual connections.  This table is
            only populated when
            {{param|#.EnablePerConnectionResults}} is {{true}}.
            A new object is created for each connection
            specified in {{param|#.NumberOfConnections}}.
            Instance numbers MUST start at 1 and sequentially
            increment as new instances are created.  All
            instances are removed when
            {{param|#.DiagnosticsState}} is set to
            {{enum|Requested|#.DiagnosticsState}} or
            {{enum|None|#.DiagnosticsState}}.";
            leaf ROMTime {
              config false;
              description
              "* For FTP this is the time at which the client
              sends the RTRV command.";
              type yang:date-and-time;
            }
            leaf BOMTime {
              config false;
              description
              "* For FTP this is the time at which the client
              receives the first data packet on the data
              connection.";
              type yang:date-and-time;
            }
            leaf EOMTime {
              config false;
              description
              "* For FTP this is the time at which the client
              receives the last packet on the data connection.";
              type yang:date-and-time;
            }
            leaf TestBytesSent {
              config false;
              description
              "The number of {{units}} of the test file sent
              during the FTP/HTTP transaction including
              FTP/HTTP headers, between {{param|BOMTime}} and
              {{param|EOMTime}}.";
              type uint32;
            }
            leaf TotalBytesReceived {
              config false;
              description
              "The total number of {{units}} (at the IP layer)
              received on the Interface between
              {{param|BOMTime}} and {{param|EOMTime}}.  This
              MAY be calculated by sampling Stats.bytesReceived
              on the {{param|#.Interface}} object at
              {{param|BOMTime}} and at {{param|EOMTime}} and
              subtracting.";
              type uint32;
            }
            leaf TotalBytesSent {
              config false;
              description
              "The total number of {{units}} (at the IP layer)
              sent on the Interface between {{param|BOMTime}}
              and {{param|EOMTime}}.  This MAY be calculated by
              sampling Stats.bytesSent on the
              {{param|#.Interface}} object at {{param|BOMTime}}
              and at {{param|EOMTime}} and subtracting.";
              type uint32;
            }
            leaf TCPOpenRequestTime {
              config false;
              description
              "* For FTP this is the time at which the TCP
              socket open (SYN) was sent for the data
              connection.";
              type yang:date-and-time;
            }
            leaf TCPOpenResponseTime {
              config false;
              description
              "* For FTP this is the time at which the TCP ACK
              to the socket opening the data connection was
              received.";
              type yang:date-and-time;
            }
          }
          list IncrementalResult {
            key "_id";
            leaf "_id" {
              type "uint32";
            }
            config false;
            description
            "Results for time segmented tests (tests where
            {{param|#.TimeBasedTestDuration}} > 0 and
            {{param|#.TimeBasedTestMeasurementInterval}} > 0).
            This data is totaled across all connections in the
            test.  A new object is created every
            {{param|#.TimeBasedTestMeasurementInterval}} after
            that interval has completed.  Instance numbers MUST
            start at 1 and sequentially increment as new
            instances are created.  All instances are removed
            when {{param|#.DiagnosticsState}} is set to
            {{enum|Requested|#.DiagnosticsState}} or
            {{enum|None|#.DiagnosticsState}}.";
            leaf TestBytesSent {
              config false;
              description
              "Change in the value of {{param|#.TestBytesSent}}
              between {{param|StartTime}} and
              {{param|EndTime}}.";
              type uint32;
            }
            leaf TotalBytesReceived {
              config false;
              description
              "The total number of {{units}} (at the IP layer)
              received on the Interface between
              {{param|StartTime}} and {{param|EndTime}}.  This
              MAY be calculated by sampling Stats.bytesReceived
              on the {{param|#.Interface}} object at
              {{param|StartTime}} and at {{param|EndTime}} and
              subtracting.";
              type uint32;
            }
            leaf TotalBytesSent {
              config false;
              description
              "The total number of {{units}} (at the IP layer)
              sent on the Interface between {{param|StartTime}}
              and {{param|EndTime}}.  This MAY be calculated by
              sampling Stats.bytesSent on the
              {{param|#.Interface}} object at
              {{param|StartTime}} and at {{param|EndTime}} and
              subtracting.";
              type uint32;
            }
            leaf StartTime {
              config false;
              description
              "For example: 2008-04-09T15:01:05.123456Z";
              type yang:date-and-time;
            }
            leaf EndTime {
              config false;
              description
              "For example: 2008-04-09T15:01:05.123456Z";
              type yang:date-and-time;
            }
          }
        }
        container UDPEchoConfig {
          description
          "This object allows the CPE to be configured to
          perform the UDP Echo Service defined in
          {{bibref|RFC862}} and UDP Echo Plus Service defined
          in {{bibref|TR-143|Appendix A.1}}.";
          leaf Enable {
            config true;
            description
            "MUST be enabled to receive UDP echo.  When enabled
            from a disabled state all related timestamps,
            statistics and UDP Echo Plus counters are cleared.";
            type boolean;
          }
          leaf Interface {
            config true;
            description
            "Note: Interfaces behind a NAT MAY require port
            forwarding rules configured in the Gateway to
            enable receiving the UDP packets.";
            type string {
              length "0..256";
            }
          }
          leaf SourceIPAddress {
            config true;
            description
            "The Source IP address of the UDP echo packet.  The
            CPE MUST only respond to a UDP echo from this
            source IP address.";
            type inet:ip-address;
          }
          leaf UDPPort {
            config true;
            description
            "The UDP port on which the UDP server MUST listen
            and respond to UDP echo requests.";
            type uint32;
          }
          leaf EchoPlusEnabled {
            config true;
            description
            "If {{true}} the CPE will perform necessary packet
            processing for UDP Echo Plus packets.";
            type boolean;
          }
          leaf EchoPlusSupported {
            config false;
            description
            "{{true}} if UDP Echo Plus is supported.";
            type boolean;
          }
          leaf PacketsReceived {
            config false;
            description
            "Incremented upon each valid UDP echo packet
            received.";
            type uint32;
          }
          leaf PacketsResponded {
            config false;
            description
            "Incremented for each UDP echo response sent.";
            type uint32;
          }
          leaf BytesReceived {
            config false;
            description
            "The number of UDP received bytes including payload
            and UDP header after the UDPEchoConfig is enabled.";
            type uint32;
          }
          leaf BytesResponded {
            config false;
            description
            "The number of UDP responded bytes, including
            payload and UDP header sent after the UDPEchoConfig
            is enabled.";
            type uint32;
          }
          leaf TimeFirstPacketReceived {
            config false;
            description
            "The time that the server receives the first UDP
            echo packet after the UDPEchoConfig is enabled.";
            type yang:date-and-time;
          }
          leaf TimeLastPacketReceived {
            config false;
            description
            "The time that the server receives the most recent
            UDP echo packet.";
            type yang:date-and-time;
          }
        }
        container UDPEchoDiagnostics {
          description
          "This object defines the diagnostics configuration for
          a UDP Echo test {{bibref|TR-143a1|Appendix A.1}}
          defined in {{bibref|RFC862}} or a UDP Echo Plus test
          defined in {{bibref|TR-143a1|Appendix A.1}}.";
          leaf DiagnosticsState {
            config true;
            description
            "While the test is in progress, setting this
            parameter to {{enum|Requested}} (and possibly
            modifying other writable parameters in this object)
            MUST result in the test being terminated and then
            restarted using the current values of the test
            parameters.";
            type enumeration {
              enum "None";
              enum "Requested";
              enum "Completed";
              enum "Error_CannotResolveHostName";
              enum "Error_Internal";
              enum "Error_Other";
            }
          }
          leaf Interface {
            config true;
            description
            "If {{empty}} is specified, the CPE MUST use the
            interface as directed by its routing policy
            (''Forwarding'' table entries) to determine the
            appropriate interface.";
            type string {
              length "0..256";
            }
          }
          leaf Host {
            config true;
            description
            "Host name or address of the host to perform tests
            to.";
            type string {
              length "0..256";
            }
          }
          leaf Port {
            config true;
            description
            "Port on the host to perform tests to.";
            type uint32 {
              range "1..65535";
            }
          }
          leaf NumberOfRepetitions {
            config true;
            description
            "Number of repetitions of the test to perform before
            reporting the results.  The default value SHOULD be
            1.";
            type uint32 {
              range "1..max";
            }
          }
          leaf Timeout {
            config true;
            description
            "Timeout in {{units}} for the test.  That is, the
            amount of time to wait for the return of a packet
            that was sent to the {{param|Host}}.";
            type uint32 {
              range "1..max";
            }
          }
          leaf DataBlockSize {
            config true;
            description
            "Size of the data block in {{units}} to be sent for
            each packet.  The default value SHOULD be 24.";
            type uint32 {
              range "1..65535";
            }
          }
          leaf DSCP {
            config true;
            description
            "DiffServ codepoint to be used for the test packets.
            The default value SHOULD be zero.";
            type uint32 {
              range "0..63";
            }
          }
          leaf InterTransmissionTime {
            config true;
            description
            "The time in {{units}} between the
            {{param|NumberOfRepetitions}} of packets sent
            during a given test.  The default value SHOULD be
            1000.";
            type uint32 {
              range "1..65535";
            }
          }
          leaf ProtocolVersion {
            config true;
            description
            "Indicates the IP protocol version to be used.  The
            default value SHOULD be {{enum|Any}}.";
            type enumeration {
              enum "Any" {
                description
                "Use either IPv4 or IPv6 depending on the system
                preference.";
              }
              enum "IPv4" {
                description
                "Use IPv4 for the requests";
              }
              enum "IPv6" {
                description
                "Use IPv6 for the requests.";
              }
            }
          }
          leaf IPAddressUsed {
            config false;
            description
            "Indicates which IP address was used to send the
            request.";
            type inet:ip-address;
          }
          leaf SuccessCount {
            config false;
            description
            "Result parameter indicating the number of
            successful packets (those in which a successful
            response was received prior to the timeout) in the
            most recent test.";
            type uint32;
          }
          leaf FailureCount {
            config false;
            description
            "Result parameter indicating the number of failed
            packets (those in which a successful response was
            not received prior to the timeout) in the most
            recent test.";
            type uint32;
          }
          leaf AverageResponseTime {
            config false;
            description
            "Result parameter indicating the average response
            time in {{units}} over all repetitions with
            successful responses of the most recent test.  If
            there were no successful responses, this value MUST
            be zero.";
            type uint32;
          }
          leaf MinimumResponseTime {
            config false;
            description
            "Result parameter indicating the minimum response
            time in {{units}} over all repetitions with
            successful responses of the most recent test.  If
            there were no successful responses, this value MUST
            be zero.";
            type uint32;
          }
          leaf MaximumResponseTime {
            config false;
            description
            "Result parameter indicating the maximum response
            time in {{units}} over all repetitions with
            successful responses of the most recent test.  If
            there were no successful responses, this value MUST
            be zero.";
            type uint32;
          }
          leaf EnableIndividualPacketResults {
            config true;
            description
            "The results must be returned in the
            {{object|IndividualPacketResult}} table for every
            repetition of the test when set to {{true}}. The
            default value SHOULD be {{false}}.";
            type boolean;
          }
          leaf IndividualPacketResultNumberOfEntries {
            config false;
            description
            "{{numentries}}";
            type uint32;
          }
          leaf UDPEchoDiagnosticsMaxResults {
            config false;
            description
            "The maximum number of rows in
            {{object|IndividualPacketResult}} that the CPE will
            store.  If a test would create more rows than
            {{param}} only the first {{param}} rows are present
            in {{object|IndividualPacketResult}}.";
            type uint32 {
              range "1..max";
            }
          }
          list IndividualPacketResult {
            key "_id";
            leaf "_id" {
              type "uint32";
            }
            config false;
            description
            "This object provides the results from individual
            UDPEchoPlus test packets collected during a test if
            {{param|#.EnableIndividualPacketResults}} is set to
            true.  When {{param|#.DiagnosticsState}} is set to
            {{enum|Completed|#.DiagnosticsState}} it should
            contain {{param|#.NumberOfRepetitions}} objects.
            Instance numbers MUST start at 1 and sequentially
            increment as new instances are created.  The
            instance number should match the
            TestIterationNumber field of the request and
            response packet.  All instances are removed when
            {{param|#.DiagnosticsState}} is set to
            {{enum|Requested|#.DiagnosticsState}} or
            {{enum|None|#.DiagnosticsState}}.";
            leaf PacketSuccess {
              config false;
              description
              "Indicates that the response to this UDP Echo Plus
              packet sent was received by the client.  When
              this value is {{true}}, then all the remaining
              parameters in this instance are valid.  Otherwise
              only the values originally set by the CPE client
              (e.g.  {{param|PacketSendTime}} and
              {{param|TestGenSN}}) MAY be set to valid values.";
              type boolean;
            }
            leaf PacketSendTime {
              config false;
              description
              "For example: 2008-04-09T15:01:05.123456Z";
              type yang:date-and-time;
            }
            leaf PacketReceiveTime {
              config false;
              description
              "If this response is never received, {{param}}
              SHOULD be set to the Unknown Time value as
              specified in {{bibref|TR-106a7|Section 3.2.2}}.";
              type yang:date-and-time;
            }
            leaf TestGenSN {
              config false;
              description
              "The TestGenSN field in the UDPEcho Plus packet
              {{bibref|TR-143a1|Section A.1.4}} sent by the CPE
              client.";
              type uint32;
            }
            leaf TestRespSN {
              config false;
              description
              "The TestRespSN field in the response packet
              {{bibref|TR-143a1|Section A.1.4}} from the UDP
              Echo Plus server (i.e.  {{param|#.Host}}) for
              this Echo Plus packet sent by the CPE client.  If
              {{param|PacketSuccess}} is {{false}}, {{param}}
              SHOULD be 0.";
              type uint32;
            }
            leaf TestRespRcvTimeStamp {
              config false;
              description
              "The TestRespRcvTimeStamp field in the response
              packet {{bibref|TR-143a1|Section A.1.4}} from the
              UDP Echo Plus server (i.e.  {{param|#.Host}}) to
              record the reception time of this UDP Echo Plus
              packet sent from the CPE client.  If
              {{param|PacketSuccess}} is {{false}}, {{param}}
              SHOULD be 0.";
              type uint32;
            }
            leaf TestRespReplyTimeStamp {
              config false;
              description
              "That is, the time that the server returned the
              UDP Echo Plus packet.  If {{param|PacketSuccess}}
              is {{false}}, {{param}} SHOULD be 0.";
              type uint32;
            }
            leaf TestRespReplyFailureCount {
              config false;
              description
              "The count value that was set by the UDP Echo Plus
              server (i.e.  {{param|#.Host}}) to record the
              number of dropped echo response packets by the
              server.  This count is incremented if a valid
              echo request packet is received at a UDP EchoPlus
              server but for some reason cannot be responded to
              (e.g.  due to local buffer overflow, CPU
              utilization, etc...).  If {{param|PacketSuccess}}
              is {{false}}, {{param}} SHOULD be 0.";
              type uint32;
            }
          }
        }
        container ServerSelectionDiagnostics {
          description
          "This object provides access to a diagnostics test
          that performs either an ICMP Ping or UDP Echo ping
          against multiple hosts determining which one has the
          smallest average response time.  There MUST be a ping
          response to the transmitted ping, or timeout, before
          the next ping is sent out.";
          leaf DiagnosticsState {
            config true;
            description
            "While the test is in progress, setting this
            parameter to {{enum|Requested}} (and possibly
            modifying other writable parameters in this
            object) MUST result in the test being terminated
            and then restarted using the current values of the
            test parameters.";
            type enumeration {
              enum "None";
              enum "Requested";
              enum "Completed";
              enum "Error_CannotResolveHostName";
              enum "Error_Internal";
              enum "Error_Other";
            }
          }
          leaf Interface {
            config true;
            description
            "If {{empty}} is specified, the CPE MUST use the
            interface as directed by its routing policy
            (''Forwarding'' table entries) to determine the
            appropriate interface.";
            type string {
              length "0..256";
            }
          }
          leaf ProtocolVersion {
            config true;
            description
            "Indicates the IP protocol version to be used.";
            type enumeration {
              enum "Any" {
                description
                "Use either IPv4 or IPv6 depending on the system
                preference.";
              }
              enum "IPv4" {
                description
                "Use IPv4 for the requests.";
              }
              enum "IPv6" {
                description
                "Use IPv6 for the requests.";
              }
            }
            default "Any";
          }
          leaf Protocol {
            config true;
            description
            "The protocol over which the test is to be
            performed.";
            type enumeration {
              enum "ICMP";
              enum "UDP Echo";
            }
          }
          leaf-list HostList {
            config true;
            description
            "Each entry is a Host name or address of a host to
            ping.";
            type string {
              length "0..256";
            }
          }
          leaf NumberOfRepetitions {
            config true;
            description
            "Number of repetitions of the ping test to perform
            for each {{param|HostList}} entry before reporting
            the results.";
            type uint32 {
              range "1..max";
            }
          }
          leaf Timeout {
            config true;
            description
            "Timeout in {{units}} for each iteration of the ping
            test where the total number of iterations is the
            value of {{param|NumberOfRepetitions}} times the
            number of entities in the {{param|HostList}}
            Parameter.";
            type uint32 {
              range "1..max";
            }
          }
          leaf FastestHost {
            config false;
            description
            "Result parameter indicating the Host (one of the
            items within the {{param|HostList}} Parameter) with
            the smallest average response time.";
            type string;
          }
          leaf MinimumResponseTime {
            config false;
            description
            "Result parameter indicating the minimum response
            time in {{units}} over all repetitions with
            successful responses of the most recent ping test
            for the Host identified in {{param|FastestHost}}.
            Success is defined by the underlying protocol used.
            If there were no successful responses across all
            Hosts, this value MUST be zero.";
            type uint32;
          }
          leaf AverageResponseTime {
            config false;
            description
            "Result parameter indicating the average response
            time in {{units}} over all repetitions with
            successful responses of the most recent ping test
            for the Host identified in {{param|FastestHost}}.
            Success is defined by the underlying protocol used.
            If there were no successful responses across all
            Hosts, this value MUST be zero.";
            type uint32;
          }
          leaf MaximumResponseTime {
            config false;
            description
            "Result parameter indicating the maximum response
            time in {{units}} over all repetitions with
            successful responses of the most recent ping test
            for the Host identified in {{param|FastestHost}}.
            Success is defined by the underlying protocol used.
            If there were no successful responses across all
            Hosts, this value MUST be zero.";
            type uint32;
          }
          leaf IPAddressUsed {
            config false;
            description
            "Indicates which IP address was used to send the
            request to the host identified in
            {{param|FastestHost}}.";
            type inet:ip-address;
          }
        }
      }
    }
    container LLDP {
      description
      "This object contains Link Layer Discovery Protocol (LLDP)
      {{bibref|802.1AB-2009}} related objects and parameters.";
      container Discovery {
        description
        "The CPE MAY, but need not, retain some or all of the
        information in this object across reboot.";
        leaf DeviceNumberOfEntries {
          config false;
          description
          "{{numentries}}";
          type uint32;
        }
        list Device {
          key "ChassisIDSubtype ChassisID";
          config false;
          description
          "This table contains information about discovered LLDP
          devices.";
          leaf Interface {
            config false;
            description
            "{{reference|the interface via which the LLDP device
            was discovered}}";
            type string;
          }
          leaf ChassisIDSubtype {
            config false;
            description
            "Note: It is assumed that this integer might be used
            for HTIP (Home-network Topology Identifying
            Protocol) {{bibref|JJ-300.00}} and
            {{bibref|G.9973}}. In this case, the Chassis ID is
            set to the representative MAC address (chassis ID
            subtype = 4) for ''HTIP-Ethernet Bridge''.";
            type uint32 {
              range "min..255";
            }
          }
          leaf ChassisID {
            config false;
            description
            "Note: It is assumed that this string might be used
            for HTIP (Home-network Topology Identifying
            Protocol) {{bibref|JJ-300.00}} and
            {{bibref|G.9973}}. In this case, the Chassis ID is
            set to the representative MAC address.  If
            ''LLDPDU''s are sent and received from two or more
            LLDP agents of the same ''HTIP-Ethernet Bridge'',
            this value is same in all ''LLDPDU''s.";
            type string {
              length "1..255";
            }
          }
          leaf-list Host {
            config false;
            description
            "When the entries are added to or removed from the
            Host tables, the value of this parameter MUST be
            updated accordingly.";
            type string {
              length "0..256";
            }
          }
          leaf PortNumberOfEntries {
            config false;
            description
            "{{numentries}}";
            type uint32;
          }
          list Port {
            key "PortIDSubtype PortID";
            config false;
            description
            "This table contains information about ports on
            discovered LLDP devices.";
            leaf PortIDSubtype {
              config false;
              description
              "* ''8-255'' (Reserved)";
              type uint32 {
                range "min..255";
              }
            }
            leaf PortID {
              config false;
              description
              "The port identifier, which is included in the
              value of the ''LLDPDU's'' Port ID TLV (TLV Type =
              2).";
              type string {
                length "1..255";
              }
            }
            leaf TTL {
              config false;
              description
              "If this value is 0, it means that the LLDP agent
              or the MAC service function of the port is
              stopped.";
              type uint32 {
                range "min..65535";
              }
            }
            leaf PortDescription {
              config false;
              description
              "Note: It is assumed that this string might be
              used for HTIP (Home-network Topology Identifying
              Protocol) {{bibref|JJ-300.00}} and
              {{bibref|G.9973}}. In this case, the parameter
              value is likely to be one of the names defined in
              {{bibref|JJ-300.00|Appendix A (''List of
              Interface Standard Names'')}}.";
              type string {
                length "0..255";
              }
            }
            leaf-list MACAddressList {
              config false;
              description
              "Note: It is assumed that it might be used for
              HTIP (Home-network Topology Identifying Protocol)
              {{bibref|JJ-300.00}} and {{bibref|G.9973}}. In
              this case, the {{bibref|OUI}} in the third octet
              is E0271A (''TTC-OUI'') and the organizationally
              defined subtype in the sixth octet is 3 (''MAC
              Address List'').";
              type yang:mac-address;
            }
            leaf LastUpdate {
              config false;
              description
              "The date and time at which the last LLDPDU was
              received for this ({{object|#}},{{object}}).";
              type yang:date-and-time;
            }
            container LinkInformation {
              description
              "Note: It is assumed that this object might be
              used for HTIP (Home-network Topology Identifying
              Protocol) {{bibref|JJ-300.00}} and
              {{bibref|G.9973}}. In this case, the
              {{bibref|OUI}} in the third octet is E0271A
              (''TTC-OUI'') and the organizationally defined
              subtype in the sixth octet is 2 (''Link
              Information'').";
              leaf InterfaceType {
                config false;
                description
                "* ''236'' (Coaxial cable)";
                type uint32;
              }
              leaf-list MACForwardingTable {
                config false;
                description
                "The port's MAC forwarding table, or the value
                is {{empty}} if no forwarding table was
                supplied.";
                type yang:mac-address;
              }
            }
          }
          container DeviceInformation {
            description
            "Note: It is assumed that this object might be used
            for HTIP (Home-network Topology Identifying
            Protocol) {{bibref|JJ-300.00}} and
            {{bibref|G.9973}}. In this case, this table
            contains the Organizationally Specific TLV (TLV
            Type = 127) of ''LLDPDU'', in which the
            {{bibref|OUI}} in the third octet is E0271A
            (''TTC-OUI'') and the organizationally defined
            subtype in the sixth octet is 1 (''Device
            Information'').";
            leaf-list DeviceCategory {
              config false;
              description
              "Note: It is assumed that this list might be used
              for HTIP (Home-network Topology Identifying
              Protocol) {{bibref|JJ-300.00}} and
              {{bibref|G.9973}}. Standard HTIP device
              categories are defined in {{bibref|JJ-300.01}}.
              In this case, the maximum length of the list is
              127 and of each item is 31, and any non-HTIP
              device categories SHOULD NOT conflict with
              standard HTIP device categories.";
              type string;
            }
            leaf ManufacturerOUI {
              config false;
              description
              "{{pattern}}";
              type string {
                length "0..6";
                pattern "^$|[0-9A-F]{6}";
              }
            }
            leaf ModelName {
              config false;
              description
              "Note: It is assumed that this string might be
              used for HTIP (Home-network Topology Identifying
              Protocol) {{bibref|JJ-300.00}} and
              {{bibref|G.9973}}.";
              type string {
                length "0..31";
              }
            }
            leaf ModelNumber {
              config false;
              description
              "Note: It is assumed that this string might be
              used for HTIP (Home-network Topology Identifying
              Protocol) {{bibref|JJ-300.00}} and
              {{bibref|G.9973}}.";
              type string {
                length "0..31";
              }
            }
            leaf VendorSpecificNumberOfEntries {
              config false;
              description
              "{{numentries}}";
              type uint32;
            }
            list VendorSpecific {
              key "OrganizationCode InformationType";
              config false;
              description
              "Note: It is assumed that this object might be
              used for HTIP (Home-network Topology Identifying
              Protocol) {{bibref|JJ-300.00}} and
              {{bibref|G.9973}}. In this case, this table
              contains the Organizationally Specific TLV (TLV
              Type = 127) of ''LLDPDU'', in which the
              {{bibref|OUI}} in the third octet is E0271A
              (''TTC-OUI''), the organizationally defined
              subtype in the sixth octet is 1 (''Device
              Information''), and the device information ID in
              the seventh octet is 255 (''Vendor-specific
              extension field'').";
              leaf OrganizationCode {
                config false;
                description
                "The vendor-specific organization code, which is
                included in the value of the ''LLDPDU's''
                Organizationally Specific TLV (TLV Type = 127).";
                type string {
                  length "6";
                  pattern "[0-9A-F]{6}";
                }
              }
              leaf InformationType {
                config false;
                description
                "The vendor-specific device information type,
                which is included in the value of the
                ''LLDPDU's'' Organizationally Specific TLV (TLV
                Type = 127).";
                type uint32 {
                  range "min..255";
                }
              }
              leaf Information {
                config false;
                description
                "The vendor-specific device information, which
                is included in the value of the ''LLDPDU's''
                Organizationally Specific TLV (TLV Type = 127).";
                type string {
                  length "0..248";
                }
              }
            }
          }
        }
      }
    }
    container IPsec {
      description
      "See the IPsec Theory of Operation
      {{bibref|TR-181i2a5|Appendix IX}} for a description of
      the working of this IPsec data model.";
      leaf Enable {
        config true;
        description
        "Enables or disables IPsec.";
        type boolean;
      }
      leaf Status {
        config false;
        description
        "The {{enum|Error}} value MAY be used by the CPE to
        indicate a locally defined error condition.";
        type enumeration {
          enum "Disabled";
          enum "Enabled";
          enum "Error";
        }
      }
      leaf AHSupported {
        config false;
        description
        "Indicates whether or not Authentication Header (AH)
        {{bibref|RFC4302}} is supported.";
        type boolean;
      }
      leaf-list IKEv2SupportedEncryptionAlgorithms {
        config false;
        description
        "As additional algorithms are added to the above
        reference, this data model will be extended according
        to the above conventions.";
        type enumeration {
          enum "DES";
          enum "3DES";
          enum "RC5";
          enum "IDEA";
          enum "CAST";
          enum "BLOWFISH";
          enum "3IDEA";
          enum "AES-CBC";
          enum "AES-CTR";
          enum "AES-CCM-8";
          enum "AES-CCM-12";
          enum "AES-CCM-16";
          enum "AES-GCM-8";
          enum "AES-GCM-12";
          enum "AES-GCM-16";
          enum "CAMELLIA-CBC";
        }
      }
      leaf-list ESPSupportedEncryptionAlgorithms {
        config false;
        description
        "As additional algorithms are added to the above
        reference, this data model will be extended according
        to the above conventions.";
        type enumeration {
          enum "NULL";
          enum "DES-IV64";
          enum "DES";
          enum "3DES";
          enum "RC5";
          enum "IDEA";
          enum "CAST";
          enum "BLOWFISH";
          enum "3IDEA";
          enum "DES-IV32";
          enum "AES-CBC";
          enum "AES-CTR";
          enum "AES-CCM-8";
          enum "AES-CCM-12";
          enum "AES-CCM-16";
          enum "AES-GCM-8";
          enum "AES-GCM-12";
          enum "AES-GCM-16";
          enum "NULL-AUTH-AES-GMAC";
          enum "CAMELLIA-CBC";
          enum "CAMELLIA-CTR";
          enum "CAMELLIA-CCM-8";
          enum "CAMELLIA-CCM-12";
          enum "CAMELLIA-CCM-16";
        }
      }
      leaf-list IKEv2SupportedPseudoRandomFunctions {
        config false;
        description
        "As additional functions are added to the above
        reference, this data model will be extended according
        to the above conventions.";
        type enumeration {
          enum "HMAC-MD5";
          enum "HMAC-SHA1";
          enum "HMAC-TIGER";
          enum "AES-128-XCBC";
          enum "HMAC-SHA2-256";
          enum "HMAC-SHA2-384";
          enum "HMAC-SHA2-512";
          enum "AES-128-CMAC";
        }
      }
      leaf-list SupportedIntegrityAlgorithms {
        config false;
        description
        "As additional algorithms are added to the above
        reference, this data model will be extended according
        to the above conventions.";
        type enumeration {
          enum "NONE";
          enum "HMAC-MD5-96";
          enum "HMAC-SHA1-96";
          enum "DES-MAC";
          enum "KPDK-MD5";
          enum "AES-XCBC-96";
          enum "HMAC-MD5-128";
          enum "HMAC-SHA1-160";
          enum "AES-CMAC-96";
          enum "AES-128-GMAC";
          enum "AES-192-GMAC";
          enum "AES-256-GMAC";
          enum "HMAC-SHA2-256-128";
          enum "HMAC-SHA2-256-192";
          enum "HMAC-SHA2-256-256";
        }
      }
      leaf-list SupportedDiffieHellmanGroupTransforms {
        config false;
        description
        "As additional algorithms are added to the above
        reference, this data model will be extended according
        to the above conventions.";
        type enumeration {
          enum "NONE";
          enum "MODP-768";
          enum "MODP-1024";
          enum "MODP-1536";
          enum "MODP-2048";
          enum "MODP-3072";
          enum "MODP-4096";
          enum "MODP-6144";
          enum "MODP-8192";
          enum "ECP-256";
          enum "ECP-384";
          enum "ECP-521";
          enum "MODP-1024-PRIME-160";
          enum "MODP-2048-PRIME-224";
          enum "MODP-2048-PRIME-256";
          enum "ECP-192";
          enum "ECP-224";
        }
      }
      leaf MaxFilterEntries {
        config false;
        description
        "A value of 0 means no specific limit.";
        type uint32;
      }
      leaf MaxProfileEntries {
        config false;
        description
        "A value of 0 means no specific limit.";
        type uint32;
      }
      leaf FilterNumberOfEntries {
        config false;
        description
        "{{numentries}}";
        type uint32;
      }
      leaf ProfileNumberOfEntries {
        config false;
        description
        "{{numentries}}";
        type uint32;
      }
      leaf TunnelNumberOfEntries {
        config false;
        description
        "{{numentries}}";
        type uint32;
      }
      leaf IKEv2SANumberOfEntries {
        config false;
        description
        "{{numentries}}";
        type uint32;
      }
      container Stats {
        description
        "The CPE MUST reset global IPsec Stats parameters
        (unless otherwise stated in individual object or
        parameter descriptions) either when IPsec is disabled
        ({{param|.IPsec.Enable}} is set to {{false}}) or when
        IPsec is enabled ({{param|.IPsec.Enable}} is set to
        {{true}}).";
        leaf NegotiationFailures {
          config false;
          description
          "The total number of times an IPsec negotiation
          failure has occurred.";
          type yang:counter32;
        }
        leaf BytesSent {
          config false;
          description
          "The total number of {{units}} sent by IPsec.";
          type yang:counter32;
        }
        leaf BytesReceived {
          config false;
          description
          "The total number of {{units}} received by IPsec.";
          type yang:counter32;
        }
        leaf PacketsSent {
          config false;
          description
          "The total number of {{units}} sent by IPsec.";
          type yang:counter32;
        }
        leaf PacketsReceived {
          config false;
          description
          "The total number of {{units}} received by IPsec.";
          type yang:counter32;
        }
        leaf ErrorsSent {
          config false;
          description
          "The total number of {{units}} discarded by IPsec due
          to any error.  This can include packets dropped due
          to a lack of transmit buffers.";
          type yang:counter32;
        }
        leaf UnknownSPIErrors {
          config false;
          description
          "The total number of {{units}} discarded by IPsec due
          to an unknown SPI (Security Parameter Index).";
          type yang:counter32;
        }
        leaf DecryptionErrors {
          config false;
          description
          "The total number of {{units}} discarded by IPsec due
          to ESP decryption errors.";
          type yang:counter32;
        }
        leaf IntegrityErrors {
          config false;
          description
          "The total number of {{units}} discarded by IPsec due
          to integrity errors.";
          type yang:counter32;
        }
        leaf ReplayErrors {
          config false;
          description
          "The total number of {{units}} discarded by IPsec due
          to replay errors.";
          type yang:counter32;
        }
        leaf PolicyErrors {
          config false;
          description
          "The total number of {{units}} discarded by IPsec due
          to policy errors.";
          type yang:counter32;
        }
        leaf OtherReceiveErrors {
          config false;
          description
          "The total number of {{units}} discarded by IPsec due
          to errors other than unknown SPI, decryption,
          integrity, replay or policy errors.  This can include
          packets dropped due to a lack of receive buffers.";
          type yang:counter32;
        }
      }
      list Filter {
        key "Alias";
        config true;
        description
        "For enabled table entries, if {{param|Interface}} is
        not a valid reference and {{param|AllInterfaces}} is
        {{false}}, then the table entry is inoperable and the
        CPE MUST set {{param|Status}} to
        {{enum|Error_Misconfigured|Status}}.";
        leaf Enable {
          config true;
          description
          "Enables or disables this IPsec Filter table entry.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Order {
          config true;
          description
          "The value of {{param}} on creation of a {{object}}
          table entry MUST be one greater than the largest
          current value (initially assigned the lowest
          precedence).";
          type uint32 {
            range "1..max";
          }
        }
        leaf Alias {
          config true;
          description
          "{{datatype|expand}}";
          type Alias;
        }
        leaf Interface {
          config true;
          description
          "This specifies the ingress interface associated with
          the entry.  It MAY be a layer 1, 2 or 3 interface.
          However, the types of interfaces for which filters
          can be instantiated is a local matter to the CPE.";
          type string {
            length "0..256";
          }
        }
        leaf AllInterfaces {
          config true;
          description
          "This specifies that all ingress interfaces are
          associated with the entry.  If {{true}}, the value of
          {{param|Interface}} is ignored since all ingress
          interfaces are indicated.";
          type boolean;
          default "false";
        }
        leaf DestIP {
          config true;
          description
          "Destination IP address.  {{empty}} indicates this
          criterion is not used, i.e.  is ''ANY''.";
          type inet:ip-address;
        }
        leaf DestMask {
          config true;
          description
          "Destination IP address mask.  If not {{empty}}, only
          the indicated network portion of the {{param|DestIP}}
          address is to be used for selection.  {{empty}}
          indicates that the full {{param|DestIP}} address is
          to be used for selection.";
          type inet:ip-address;
        }
        leaf DestIPExclude {
          config true;
          description
          "If {{true}}, the rule matches all packets except
          those that match the (masked) {{param|DestIP}} entry,
          if specified.";
          type boolean;
          default "false";
        }
        leaf SourceIP {
          config true;
          description
          "Source IP address.  {{empty}} indicates this
          criterion is not used, i.e.  is ''ANY''.";
          type inet:ip-address;
        }
        leaf SourceMask {
          config true;
          description
          "Source IP address mask.  If not {{empty}}, only the
          indicated network portion of the {{param|SourceIP}}
          address is to be used for selection.  {{empty}}
          indicates that the full {{param|SourceIP}} address is
          to be used for selection.";
          type inet:ip-address;
        }
        leaf SourceIPExclude {
          config true;
          description
          "If {{true}}, the rule matches all packets except
          those that match the (masked) {{param|SourceIP}}
          entry, if specified.";
          type boolean;
          default "false";
        }
        leaf Protocol {
          config true;
          description
          "Note that {{bibref|RFC4301}} refers to this as the
          ''Next Layer Protocol''.  It is obtained from the
          IPv4 ''Protocol'' or the IPv6 ''Next Header'' fields.";
          type int32 {
            range "-1..255";
          }
          default "-1";
        }
        leaf ProtocolExclude {
          config true;
          description
          "If {{true}}, the rule matches all packets except
          those that match {{param|Protocol}}, if specified.";
          type boolean;
          default "false";
        }
        leaf DestPort {
          config true;
          description
          "The value of this parameter is ignored for protocols
          that do not use ports, e.g.  ICMP (1).";
          type int32 {
            range "-1..65535";
          }
          default "-1";
        }
        leaf DestPortRangeMax {
          config true;
          description
          "A value of -1 indicates that no destination port
          range is specified.";
          type int32 {
            range "-1..65535";
          }
          default "-1";
        }
        leaf DestPortExclude {
          config true;
          description
          "If {{true}}, the rule matches all packets except
          those that match {{param|DestPort}} (or port range),
          if specified.";
          type boolean;
          default "false";
        }
        leaf SourcePort {
          config true;
          description
          "The value of this parameter is ignored for protocols
          that do not use ports, e.g.  ICMP (1).";
          type int32 {
            range "-1..65535";
          }
          default "-1";
        }
        leaf SourcePortRangeMax {
          config true;
          description
          "A value of -1 indicates that no source port range is
          specified.";
          type int32 {
            range "-1..65535";
          }
          default "-1";
        }
        leaf SourcePortExclude {
          config true;
          description
          "If {{true}}, the rule matches all packets except
          those that match {{param|SourcePort}} (or port
          range), if specified.";
          type boolean;
          default "false";
        }
        leaf ProcessingChoice {
          config true;
          description
          "Indicates how packets that match this rule will be
          processed {{bibref|RFC4301|Section 4.4.1}}.";
          type enumeration {
            enum "Discard" {
              description
              "Packet is not allowed to traverse the IPsec
              boundary; packet will be discarded";
            }
            enum "Bypass" {
              description
              "Packet is allowed to bypass traverse the IPsec
              boundary without protection";
            }
            enum "Protect" {
              description
              "Packet is afforded protection as specified by
              {{param|Profile}}";
            }
          }
          default "Bypass";
        }
        leaf Profile {
          config true;
          description
          "Any changes to the referenced profile will have an
          immediate effect on any established IPsec tunnels.
          Such changes will often force IKEv2 sessions and
          child SAs to be re-established.";
          type string;
        }
      }
      list Profile {
        key "Alias";
        config true;
        description
        "Profile table that represents the IPsec Security Policy
        Database (SPD) {{bibref|RFC4301|Section 4.4.1}}
        processing info.  Each entry defines the IPsec
        treatment for packets that match the
        {{object|#.Filter}} entries that reference the entry.";
        leaf Alias {
          config true;
          description
          "{{datatype|expand}}";
          type Alias;
        }
        leaf MaxChildSAs {
          config true;
          description
          "Note that support for more than one child SA pair per
          IKEv2 session is OPTIONAL {{bibref|RFC5996|Section
          1.3}}.";
          type uint32;
        }
        leaf-list RemoteEndpoints {
          config true;
          description
          "The host name or IP address of the remote IPsec
          tunnel endpoint.  If more than one name/address is
          supplied, they will be tried in turn, i.e.  they are
          in decreasing order of precedence.";
          type string {
            length "0..64";
          }
        }
        leaf ForwardingPolicy {
          config true;
          description
          "The forwarding policy can be referenced by entries in
          the {{object|##.Routing.Router.{i}.IPv4Forwarding}}
          and {{object|##.Routing.Router.{i}.IPv6Forwarding}}
          tables, and therefore allows SPD selection criteria
          to influence the forwarding decision.";
          type uint32;
          default "0";
        }
        leaf Protocol {
          config true;
          description
          "This is not to be confused with
          {{object|#.Filter}}.{{param|#.Filter.{i}.Protocol}},
          which is an SPD selector that can select packets that
          already have AH or ESP headers.  {{object}}.{{param}}
          selects whether AH or ESP will be used when
          encapsulating a packet.";
          type enumeration {
            enum "AH" {
              description
              "Authentication Header {{bibref|RFC4302}}; can
              only be selected if {{param|#.AHSupported}} is
              {{true}}";
            }
            enum "ESP" {
              description
              "Encapsulating Security Payload {{bibref|RFC4303}}";
            }
          }
          default "ESP";
        }
        leaf IKEv2AuthenticationMethod {
          config true;
          description
          "If {{empty}}, or the referenced row is disabled or
          deleted, the CPE chooses the authentication method
          based on local policy.";
          type string;
        }
        leaf-list IKEv2AllowedEncryptionAlgorithms {
          config true;
          description
          "Allowed IKEv2 encryption algorithms.";
          type string;
          must ". = ../../../IPsec/IKEv2SupportedEncryptionAlgorithms";
        }
        leaf-list ESPAllowedEncryptionAlgorithms {
          config true;
          description
          "Allowed ESP encryption algorithms.";
          type string;
          must ". = ../../../IPsec/ESPSupportedEncryptionAlgorithms";
        }
        leaf-list IKEv2AllowedPseudoRandomFunctions {
          config true;
          description
          "Allowed IKEv2 pseudo-random functions.";
          type string;
          must ". = ../../../IPsec/IKEv2SupportedPseudoRandomFunctions";
        }
        leaf-list IKEv2AllowedIntegrityAlgorithms {
          config true;
          description
          "Allowed IKEv2 integrity algorithms.";
          type string;
          must ". = ../../../IPsec/SupportedIntegrityAlgorithms";
        }
        leaf-list AHAllowedIntegrityAlgorithms {
          config true;
          description
          "Allowed AH integrity algorithms
          {{bibref|IKEv2-params|Transform Type 3}}
          {{bibref|RFC4835|Section 3.2}}.";
          type string;
          must ". = ../../../IPsec/SupportedIntegrityAlgorithms";
        }
        leaf-list ESPAllowedIntegrityAlgorithms {
          config true;
          description
          "Allowed ESP integrity algorithms
          {{bibref|IKEv2-params|Transform Type 3}}
          {{bibref|RFC4835|Section 3.1.1}}.";
          type string;
          must ". = ../../../IPsec/SupportedIntegrityAlgorithms";
        }
        leaf-list IKEv2AllowedDiffieHellmanGroupTransforms {
          config true;
          description
          "Allowed IKEv2 Diffie-Hellman group transforms.";
          type string;
          must ". = ../../../IPsec/SupportedDiffieHellmanGroupTransforms";
        }
        leaf IKEv2DeadPeerDetectionTimeout {
          config true;
          description
          "IKEv2 Dead Peer Detection (DPD) timeout in {{units}}.
          {{bibref|RFC5996|section 2.4}}";
          type uint32;
        }
        leaf IKEv2NATTKeepaliveTimeout {
          config true;
          description
          "IKEv2 NAT traversal (NAT-T) keepalive timeout in
          {{units}}.  {{bibref|RFC3948|Section 4}}";
          type uint32;
        }
        leaf AntiReplayWindowSize {
          config true;
          description
          "A value of 0 means that Sequence Number Verification
          is disabled.";
          type uint32;
          default "0";
        }
        leaf DoNotFragment {
          config true;
          description
          "Controls the value of the ''Do Not Fragment'' (DF)
          bit.  {{bibref|RFC4301|Section 8.1}}";
          type enumeration {
            enum "Set";
            enum "Clear";
            enum "Copy" {
              description
              "Copy from inner header; applies only when both
              inner and outer headers are IPv4";
            }
          }
        }
        leaf DSCPMarkPolicy {
          config true;
          description
          "Automatic DSCP marking behavior is a local matter to
          the CPE, possibly influenced by other Broadband Forum
          standards that it supports.";
          type int32 {
            range "-2..63";
          }
        }
        leaf IKEv2SATrafficLimit {
          config true;
          description
          "If both {{param}} and {{param|IKEv2SATimeLimit}} are
          non-zero, the IKEv2 SA is deleted when the first
          limit is reached.";
          type uint64;
        }
        leaf IKEv2SATimeLimit {
          config true;
          description
          "If both {{param}} and {{param|IKEv2SATrafficLimit}}
          are non-zero, the IKEv2 SA is deleted when the first
          limit is reached.";
          type uint32;
        }
        leaf IKEv2SAExpiryAction {
          config true;
          description
          "Action to take when an IKEv2 SA expires, whether as a
          result of hitting a traffic limit or a time limit.";
          type enumeration {
            enum "Renegotiate";
            enum "Delete";
          }
        }
        leaf ChildSATrafficLimit {
          config true;
          description
          "If both {{param}} and {{param|ChildSATimeLimit}} are
          non-zero, the child SA is deleted when the first
          limit is reached.";
          type uint64;
        }
        leaf ChildSATimeLimit {
          config true;
          description
          "If both {{param}} and {{param|ChildSATrafficLimit}}
          are non-zero, the child SA is deleted when the first
          limit is reached.";
          type uint32;
        }
        leaf ChildSAExpiryAction {
          config true;
          description
          "Action to take when a Child SA expires, whether as a
          result of hitting a traffic limit or a time limit.";
          type enumeration {
            enum "Renegotiate";
            enum "Delete";
          }
        }
        leaf SentCPAttrNumberOfEntries {
          config false;
          description
          "{{numentries}}";
          type uint32;
        }
        list SentCPAttr {
          key "Type";
          unique "Alias";
          config true;
          description
          "Each instance of this object represents an IKEv2
          Configuration Payload (CP) {{bibref|RFC5996|Section
          3.15}} Attribute that MUST, if enabled, be sent in
          IKEv2 CP CFG_REQUEST messages.  All such Attributes
          MUST be listed.";
          leaf Enable {
            config true;
            description
            "Enables or disables this {{object}} entry.";
            type boolean;
          }
          leaf Alias {
            config true;
            description
            "{{datatype|expand}}";
            type Alias;
          }
          leaf Type {
            config true;
            description
            "CP Attribute Type as described in
            {{bibref|RFC5996|Section 3.15.1}} and defined in
            {{bibref|IKEv2-params|IKEv2 Configuration Payload
            Attribute Types}}.";
            type uint32 {
              range "0..32767";
            }
          }
          leaf Value {
            config true;
            description
            "A hexbinary encoded CP Attribute Value as described
            in {{bibref|RFC5996|Section 3.15.1}} and defined in
            {{bibref|IKEv2-params|IKEv2 Configuration Payload
            Attribute Types}}.";
            type yang:hex-string {
              length "0..65535";
            }
          }
        }
      }
      list Tunnel {
        key "TunnelInterface TunneledInterface";
        unique "Alias";
        config true;
        description
        "Each instance's {{param|Filters}} parameter references
        the {{object|#.Filter}} instances that require the
        {{object}} instance to exist.  If this list ever
        becomes {{empty}}, e.g.  because all the referenced
        {{object|#.Filter}} instances have been disabled or
        deleted, the CPE MAY choose not to delete the
        {{object}} instance (and its associated
        ({{enum|Tunnel|.IP.Interface.{i}.Type}},{{enum|Tunneled|.IP.Interface.{i}.Type}})
        {{object|.IP.Interface}} pair).  This can be desirable,
        because {{object|.QoS.Classification}},
        {{object|.Routing.Router.{i}.IPv4Forwarding}},
        {{object|.Routing.Router.{i}.IPv6Forwarding}} etc
        instances might be referencing the
        {{object|.IP.Interface}} instances.";
        leaf Alias {
          config true;
          description
          "{{datatype|expand}}";
          type Alias;
        }
        leaf TunnelInterface {
          config true;
          description
          "The corresponding auto-created
          {{enum|Tunnel|Device.IP.Interface.{i}.Type}}
          {{object|.IP.Interface}} instance.
          {{reference||delete}}";
          type string;
        }
        leaf TunneledInterface {
          config true;
          description
          "The corresponding auto-created
          {{enum|Tunneled|Device.IP.Interface.{i}.Type}}
          {{object|.IP.Interface}} instance.
          {{reference||delete}}";
          type string;
        }
        leaf-list Filters {
          config false;
          description
          "The {{object|#.Filter}} instances that require this
          {{object}} instance to exist.  {{reference}}";
          type string;
        }
        container Stats {
          description
          "Note that this object does not include generic
          statistics that are available in the associated
          {{object|.IP.Interface.{i}.Stats}} object.";
          leaf DecryptionErrors {
            config false;
            description
            "The total number of inbound {{units}} discarded due
            to ESP decryption errors.";
            type yang:counter32;
          }
          leaf IntegrityErrors {
            config false;
            description
            "The total number of inbound {{units}} discarded due
            to integrity errors.";
            type yang:counter32;
          }
          leaf ReplayErrors {
            config false;
            description
            "The total number of inbound {{units}} discarded due
            to replay errors.";
            type yang:counter32;
          }
          leaf PolicyErrors {
            config false;
            description
            "The total number of inbound {{units}} discarded due
            to policy errors.";
            type yang:counter32;
          }
          leaf OtherReceiveErrors {
            config false;
            description
            "The total number of inbound {{units}} discarded due
            to errors other than decryption, integrity, replay
            or policy errors.  This can include packets dropped
            due to a lack of receive buffers.";
            type yang:counter32;
          }
        }
      }
      list IKEv2SA {
        key "Tunnel";
        config true;
        description
        "Represents an IKEv2 Security Association (SA),
        corresponding to an IKEv2 session.  Instances are
        automatically created and deleted as IKEv2 SAs are
        created and deleted.";
        leaf Status {
          config false;
          description
          "The current operational state of the IKEv2 SA.";
          type enumeration {
            enum "Up";
            enum "Down";
            enum "Unknown";
            enum "Dormant";
            enum "Error";
          }
        }
        leaf Alias {
          config true;
          description
          "{{datatype|expand}}";
          type Alias;
        }
        leaf Tunnel {
          config true;
          description
          "Note that {{param}} is a unique key, i.e only one
          {{object}} instance is associated with a given
          {{object|#.Tunnel}} instance.  During rekeying
          {{bibref|RFC5996|Section 2.8}}, a new IKEv2 SA is
          created and inherits the existing IKEv2 SA's child
          SAs, then the old IKEv2 SA is deleted.  From the
          management point of view the new and old IKEv2 SAs
          are the same SA and MUST be modeled using the same
          {{object}} instance.";
          type string;
        }
        leaf LocalAddress {
          config false;
          description
          "The local IP address that this IKEv2 SA was
          negotiated with.  This is assigned via IKEv2 and will
          also be available via the associated
          {{object|#.Tunnel}}'s
          {{param|#.Tunnel.{i}.TunnelInterface}}
          {{object|##.IP.Interface.{i}.IPv4Address}} or
          {{object|##.IP.Interface.{i}.IPv6Address}} table (as
          appropriate).";
          type inet:ip-address;
        }
        leaf RemoteAddress {
          config false;
          description
          "The IP address of the peer that this IKEv2 SA was
          negotiated with.  This will be the IP address of one
          of the security gateways configured via
          {{param|#.Profile.{i}.RemoteEndpoints}}.";
          type inet:ip-address;
        }
        leaf EncryptionAlgorithm {
          config false;
          description
          "This will be one of the
          {{param|#.Profile.{i}.IKEv2AllowedEncryptionAlgorithms}}
          from the {{object|#.Profile}} instance via which this
          IKEv2 SA was created.";
          type string {
            length "0..64";
          }
        }
        leaf EncryptionKeyLength {
          config false;
          description
          "The value is 0 if the key length is implicit in the
          specified algorithm or there is no encryption
          applied.";
          type uint32;
        }
        leaf PseudoRandomFunction {
          config false;
          description
          "This will be one of the
          {{param|#.Profile.{i}.IKEv2AllowedPseudoRandomFunctions}}
          from the {{object|#.Profile}} instance via which this
          IKEv2 SA was created.";
          type string {
            length "0..64";
          }
        }
        leaf IntegrityAlgorithm {
          config false;
          description
          "This will be one of the
          {{param|#.Profile.{i}.IKEv2AllowedIntegrityAlgorithms}}
          from the {{object|#.Profile}} instance via which this
          IKEv2 SA was created.";
          type string {
            length "0..64";
          }
        }
        leaf DiffieHellmanGroupTransform {
          config false;
          description
          "This will be one of the
          {{param|#.Profile.{i}.IKEv2AllowedDiffieHellmanGroupTransforms}}
          from the {{object|#.Profile}} instance via which this
          IKEv2 SA was created.";
          type string {
            length "0..64";
          }
        }
        leaf CreationTime {
          config false;
          description
          "When this IKEv2 SA was set up.";
          type yang:date-and-time;
        }
        leaf NATDetected {
          config false;
          description
          "Whether NAT traversal is supported by the device and,
          if so, whether a NAT was detected.";
          type enumeration {
            enum "None";
            enum "Local";
            enum "Remote";
            enum "Unsupported";
          }
        }
        leaf ReceivedCPAttrNumberOfEntries {
          config false;
          description
          "{{numentries}}";
          type uint32;
        }
        leaf ChildSANumberOfEntries {
          config false;
          description
          "{{numentries}}";
          type uint32;
        }
        container Stats {
          description
          "The CPE MUST reset the IKEv2 SA's Stats parameters
          (unless otherwise stated in individual object or
          parameter descriptions) whenever the associated
          {{param|#.Tunnel}} instance's Stats parameters are
          reset.";
          leaf BytesSent {
            config false;
            description
            "The total number of {{units}} handled in the
            outbound direction by the IKEv2 SA.";
            type yang:counter32;
          }
          leaf BytesReceived {
            config false;
            description
            "The total number of {{units}} handled in the
            inbound direction by the IKEv2 SA.";
            type yang:counter32;
          }
          leaf PacketsSent {
            config false;
            description
            "The total number of {{units}} handled in the
            outbound direction by the IKEv2 SA.";
            type yang:counter32;
          }
          leaf PacketsReceived {
            config false;
            description
            "The total number of {{units}} handled in the
            inbound direction by the IKEv2 SA.";
            type yang:counter32;
          }
          leaf ErrorsSent {
            config false;
            description
            "Note that this refers to IKE protocol {{units}},
            and not to {{units}} carried by other SAs.";
            type yang:counter32;
          }
          leaf DecryptionErrors {
            config false;
            description
            "Note that this refers to IKEv2 protocol {{units}},
            and not to {units}} carried by other SAs.";
            type yang:counter32;
          }
          leaf IntegrityErrors {
            config false;
            description
            "Note that this refers to IKEv2 protocol {{units}},
            and not to {{units}} carried by other SAs.";
            type yang:counter32;
          }
          leaf OtherReceiveErrors {
            config false;
            description
            "Note that this refers to IKEv2 protocol {{units}},
            and not to {{units}} carried by other SAs.";
            type yang:counter32;
          }
        }
        list ReceivedCPAttr {
          key "_id";
          leaf "_id" {
            type "uint32";
          }
          config true;
          description
          "If the same Attribute is received multiple times, it
          is up to the CPE to decide which entries to include
          (i.e.  whether the same Attribute will be present
          multiple times). In order to allow for the same
          Attribute to be present multiple times within the
          table, this table has no unique key defined.";
          leaf Type {
            config false;
            description
            "CP Attribute Type as described in
            {{bibref|RFC5996|Section 3.15.1}} and defined in
            {{bibref|IKEv2-params|IKEv2 Configuration Payload
            Attribute Types}}.";
            type uint32 {
              range "0..32767";
            }
          }
          leaf Value {
            config false;
            description
            "A hexbinary encoded CP Attribute Value as described
            in {{bibref|RFC5996|Section 3.15.1}} and defined in
            {{bibref|IKEv2-params|IKEv2 Configuration Payload
            Attribute Types}}.";
            type yang:hex-string {
              length "0..65535";
            }
          }
        }
        list ChildSA {
          key "InboundSPI";
          unique "OutboundSPI";
          config true;
          description
          "Represents a child Security Association (SA) pair,
          i.e.  an inbound child SA and an outbound child SA.";
          leaf Status {
            config false;
            description
            "The current operational state of the child SA pair.";
            type enumeration {
              enum "Up";
              enum "Down";
              enum "Unknown";
              enum "Dormant";
              enum "Error";
            }
          }
          leaf Alias {
            config true;
            description
            "{{datatype|expand}}";
            type Alias;
          }
          leaf InboundSPI {
            config true;
            description
            "The inbound child SA's Security Parameter Index
            (SPI).";
            type uint32;
          }
          leaf OutboundSPI {
            config false;
            description
            "The outbound child SA's Security Parameter Index
            (SPI).";
            type uint32;
          }
          leaf CreationTime {
            config false;
            description
            "The date and time when the child SA was created.";
            type yang:date-and-time;
          }
          container Stats {
            description
            "The CPE MUST reset the child SA's Stats parameters
            (unless otherwise stated in individual object or
            parameter descriptions) whenever the parent
            {{object|#}} instance's Stats parameters are reset.";
            leaf BytesSent {
              config false;
              description
              "The number of {{units}} handled by the outbound
              child SA.";
              type yang:counter32;
            }
            leaf BytesReceived {
              config false;
              description
              "The number of {{units}} handled by the inbound
              child SA.";
              type yang:counter32;
            }
            leaf PacketsSent {
              config false;
              description
              "The number of {{units}} handled by the outbound
              child SA.";
              type yang:counter32;
            }
            leaf PacketsReceived {
              config false;
              description
              "The number of {{units}} handled by the inbound
              child SA.";
              type yang:counter32;
            }
            leaf ErrorsSent {
              config false;
              description
              "The number of {{units}} discarded by the outbound
              child SA due to any error.  This can include
              compression errors or errors due to a lack of
              transmit buffers.";
              type yang:counter32;
            }
            leaf DecryptionErrors {
              config false;
              description
              "The number of {{units}} discarded by the inbound
              child SA due to decryption errors.";
              type yang:counter32;
            }
            leaf IntegrityErrors {
              config false;
              description
              "The number of {{units}} discarded by the inbound
              child SA due to integrity errors.";
              type yang:counter32;
            }
            leaf ReplayErrors {
              config false;
              description
              "The number of {{units}} discarded by the inbound
              child SA due to replay errors.";
              type yang:counter32;
            }
            leaf PolicyErrors {
              config false;
              description
              "The number of {{units}} discarded by the inbound
              child SA due to policy errors.";
              type yang:counter32;
            }
            leaf OtherReceiveErrors {
              config false;
              description
              "The number of {{units}} discarded by the inbound
              child SA due to errors other than decryption,
              integrity, replay or policy errors.  This can
              include decompression errors or errors due to a
              lack of receive buffers.";
              type yang:counter32;
            }
          }
        }
      }
    }
    container GRE {
      description
      "This object contains parameters associated with the
      Generic Routing Encapsulation (GRE) Tunnel
      ({{bibref|RFC2784}}) with Key and Sequence Number
      extensions ({{bibref|RFC2890}}). This object also
      provides a means to treat packets that are encapsulated
      within a GRE Tunnel by using a set of {{object|Filter}}
      objects to determine the treatment of the packet.";
      leaf TunnelNumberOfEntries {
        config false;
        description
        "{{numentries}}";
        type uint32;
      }
      leaf FilterNumberOfEntries {
        config false;
        description
        "{{numentries}}";
        type uint32;
      }
      list Tunnel {
        key "Alias";
        config true;
        description
        "GRE Tunnel table, models the GRE Tunnel instance and
        represents the entry point and exit point of the tunnel
        in relation to the WAN interface.  A {{object}} object
        has one or more {{object|Interface}} objects that
        further define the sessions or flows within the tunnel.";
        leaf Enable {
          config true;
          description
          "Enables or disables the tunnel.";
          type boolean;
        }
        leaf Status {
          config false;
          description
          "The current operational state of the tunnel.";
          type enumeration {
            enum "Disabled";
            enum "Enabled";
            enum "Error";
          }
        }
        leaf Alias {
          config true;
          description
          "{{datatype|expand}}";
          type Alias;
        }
        leaf-list RemoteEndpoints {
          config true;
          description
          "The Fully Qualified Domain Name (FQDN) or IP address
          of the remote GRE tunnel endpoint.  If more than one
          name/address is supplied, they will be tried in turn,
          i.e.  they are in decreasing order of precedence.";
          type string {
            length "0..256";
          }
        }
        leaf KeepAlivePolicy {
          config true;
          description
          "The mechanism used to keep the tunnel from timing out
          at the {{param|ConnectedRemoteEndpoint}}.";
          type enumeration {
            enum "ICMP";
            enum "None";
          }
          default "None";
        }
        leaf KeepAliveTimeout {
          config true;
          description
          "The tunnel keepalive timeout in {{units}}.";
          type uint32;
          default "10";
        }
        leaf KeepAliveThreshold {
          config true;
          description
          "Number of KeepAlive messages unacknowledged by the
          {{param|ConnectedRemoteEndpoint}} before the
          {{object}} is perceived failed.";
          type uint32;
          default "3";
        }
        leaf DeliveryHeaderProtocol {
          config true;
          description
          "The protocol used for the delivery header.";
          type enumeration {
            enum "IPv4";
            enum "IPv6";
          }
        }
        leaf DefaultDSCPMark {
          config true;
          description
          "If the specified entries in the {{object|#.Filter}}
          table do not match this {{object}} object or an
          instance of the {{object|Interface}} object for this
          {{object}} object, then the value of this parameter
          is applied to the delivery header of the packets in
          this {{object}}.";
          type uint32;
          default "0";
        }
        leaf ConnectedRemoteEndpoint {
          config false;
          description
          "The Fully Qualified Domain Name (FQDN) name or IP
          address of the connected remote GRE tunnel endpoint.";
          type string {
            length "0..256";
          }
        }
        leaf InterfaceNumberOfEntries {
          config false;
          description
          "{{numentries}}";
          type uint32;
        }
        container Stats {
          description
          "The device MUST reset the tunnel's Stats parameters
          (unless otherwise stated in individual object or
          parameter descriptions) either when the tunnel
          becomes operationally down due to a previous
          administrative down (i.e., Status parameter
          transitions to a disabled state after the tunnel has
          been disabled) or when the tunnel becomes
          administratively up (i.e.  the Enable parameter
          transitioned from {{false}} to {{true}}).";
          leaf KeepAliveSent {
            config false;
            description
            "The total number of KeepAlive {{units}} sent out
            the tunnel.";
            type yang:counter32;
          }
          leaf KeepAliveReceived {
            config false;
            description
            "The total number of KeepAlive {{units}} received by
            the tunnel.";
            type yang:counter32;
          }
          leaf BytesSent {
            config false;
            description
            "The total number of {{units}} sent by the tunnel.";
            type yang:counter32;
          }
          leaf BytesReceived {
            config false;
            description
            "The total number of {{units}} received by the
            tunnel.";
            type yang:counter32;
          }
          leaf PacketsSent {
            config false;
            description
            "The total number of {{units}} sent by the tunnel.";
            type yang:counter32;
          }
          leaf PacketsReceived {
            config false;
            description
            "The total number of {{units}} received by the
            tunnel.";
            type yang:counter32;
          }
          leaf ErrorsSent {
            config false;
            description
            "The total number of {{units}} discarded by the
            tunnel due to any error.  This can include packets
            dropped due to a lack of transmit buffers.";
            type yang:counter32;
          }
          leaf ErrorsReceived {
            config false;
            description
            "The total number of {{units}} received by the
            tunnel that contained errors preventing them from
            being delivered to a higher-layer protocol.";
            type yang:counter32;
          }
        }
        list Interface {
          key "Name";
          unique "Alias";
          config true;
          description
          "GRE Interface table (a stackable interface object as
          described in {{bibref|TR-181i2|Section 4.2}}). The
          {{object}} object models the GRE Header as defined in
          {{bibref|RFC2784}} and extensions to the GRE Header
          as defined in {{bibref|RFC2890}}. The {{object}}
          object provides a way to discriminate how sessions or
          flows are encapsulated within the GRE Tunnel.  In
          addition the {{object}} object represents the entry
          point and exit point of the tunnel in relation to the
          LAN interface.  Unless the Key Identifier of
          {{bibref|RFC2890}} is supported there is only one
          instance of this {{object}} object per tunnel.";
          leaf Enable {
            config true;
            description
            "This parameter is based on ''ifAdminStatus'' from
            {{bibref|RFC2863}}.";
            type boolean;
          }
          leaf Status {
            config false;
            description
            "This parameter is based on ''ifOperStatus'' from
            {{bibref|RFC2863}}.";
            type enumeration {
              enum "Up";
              enum "Down";
              enum "Unknown";
              enum "Dormant";
              enum "NotPresent";
              enum "LowerLayerDown";
              enum "Error";
            }
          }
          leaf Alias {
            config true;
            description
            "{{datatype|expand}}";
            type Alias;
          }
          leaf Name {
            config true;
            description
            "The textual name of the interface as assigned by
            the CPE.";
            type string {
              length "0..64";
            }
          }
          leaf LastChange {
            config false;
            description
            "The accumulated time in {{units}} since the
            interface entered its current operational state.";
            type uint32;
          }
          leaf-list LowerLayers {
            config true;
            description
            "{{list}} {{reference|an interface object that is
            stacked immediately below this interface object}}
            See {{bibref|TR-181i2|Section 4.2.1}}.";
            type string;
          }
          leaf ProtocolIdOverride {
            config true;
            description
            "The Protocol ID assigned to this {{object}}. The
            Protocol Id is the EtherType value used to identify
            the encapsulated payload.  When set to {{null}} the
            CPE determines the Protocol Id.";
            type uint32;
            default "0";
          }
          leaf UseChecksum {
            config true;
            description
            "When {{true}}, includes the \"Checksum\" field in
            the GRE header as defined in {{bibref|RFC2784}}.";
            type boolean;
            default "false";
          }
          leaf KeyIdentifierGenerationPolicy {
            config true;
            description
            "The method used to generate the Key Identifier
            extension as defined in.{{bibref|RFC2890}}.";
            type enumeration {
              enum "Disabled";
              enum "Provisioned";
              enum "CPE_Generated" {
                description
                "The generation of the Key field is CPE specific
                implementation.";
              }
            }
            default "Disabled";
          }
          leaf KeyIdentifier {
            config true;
            description
            "When the value of
            {{param|KeyIdentifierGenerationPolicy}} is
            {{enum|Provisioned|KeyIdentifierGenerationPolicy}}
            this {{param}} parameter is used to identify an
            individual traffic flow within a GRE tunnel, as
            defined in {{bibref|RFC2890}}.";
            type uint32;
            default "0";
          }
          leaf UseSequenceNumber {
            config true;
            description
            "When {{true}}, includes the \"SequenceNumber\"
            field in the GRE header as defined in
            {{bibref|RFC2890}}";
            type boolean;
            default "false";
          }
          container Stats {
            description
            "The device MUST reset the interface's Stats
            parameters (unless otherwise stated in individual
            object or parameter descriptions) either when the
            interface becomes operationally down due to a
            previous administrative down (i.e., the interface's
            Status parameter transitions to a down state after
            the interface has been disabled) or when the
            interface becomes administratively up (i.e.  the
            Enable parameter transitioned from {{false}} to
            {{true}}).";
            leaf BytesSent {
              config false;
              description
              "The total number of {{units}} sent by this
              interface.";
              type yang:counter32;
            }
            leaf BytesReceived {
              config false;
              description
              "The total number of {{units}} received by this
              interface.";
              type yang:counter32;
            }
            leaf PacketsSent {
              config false;
              description
              "The total number of {{units}} sent by this
              interface.";
              type yang:counter32;
            }
            leaf PacketsReceived {
              config false;
              description
              "The total number of {{units}} received by this
              interface.";
              type yang:counter32;
            }
            leaf ErrorsSent {
              config false;
              description
              "The total number of {{units}} discarded by this
              interface due to any error.  This can include
              packets dropped due to a lack of transmit
              buffers.";
              type yang:counter32;
            }
            leaf ErrorsReceived {
              config false;
              description
              "The total number of {{units}} received by this
              interface that contained errors preventing them
              from being delivered to a higher-layer protocol.";
              type yang:counter32;
            }
            leaf DiscardChecksumReceived {
              config false;
              description
              "The total number of {{units}} received by the
              tunnel interface that are discarded because of
              Checksum errors.";
              type yang:counter32;
            }
            leaf DiscardSequenceNumberReceived {
              config false;
              description
              "The total number of {{units}} received by the
              tunnel interface that are discarded because of
              Sequence Number errors.";
              type yang:counter32;
            }
          }
        }
      }
      list Filter {
        key "Alias";
        config true;
        description
        "For enabled table entries, if {{param|Interface}} is
        not a valid reference and {{param|AllInterfaces}} is
        {{false}}, then the table entry is inoperable and the
        CPE MUST set {{param|Status}} to
        {{enum|Error_Misconfigured|Status}}.";
        leaf Enable {
          config true;
          description
          "Enables or disables this filter.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Order {
          config true;
          description
          "The value of {{param}} on creation of a {{object}}
          table entry MUST be one greater than the largest
          current value (initially assigned the lowest
          precedence).";
          type uint32 {
            range "1..max";
          }
        }
        leaf Alias {
          config true;
          description
          "{{datatype|expand}}";
          type Alias;
        }
        leaf Interface {
          config true;
          description
          "Filter criterion.  {{reference}}";
          type string {
            length "0..256";
          }
        }
        leaf AllInterfaces {
          config true;
          description
          "Filter criterion.  This specifies that all ingress
          GRE tunnel interfaces are associated with the entry.
          If {{true}}, the value of {{param|Interface}} is
          ignored since all ingress GRE tunnel interfaces are
          indicated.";
          type boolean;
          default "false";
        }
        leaf VLANIDCheck {
          config true;
          description
          "Current outer Ethernet VLAN ID as defined in 802.1Q.
          A value of -1 indicates this criterion is not used
          for filtering.";
          type int32 {
            range "-1..max";
          }
          default "-1";
        }
        leaf VLANIDExclude {
          config true;
          description
          "If {{true}}, the filter includes all packets except
          those that match the {{param|VLANIDCheck}} entry, if
          specified.";
          type boolean;
          default "false";
        }
        leaf DSCPMarkPolicy {
          config true;
          description
          "* A value of -2 indicates automatic marking of DSCP.";
          type int32 {
            range "-2..63";
          }
        }
      }
    }
    container L2TPv3 {
      description
      "This object also provides a means to treat packets that
      are encapsulated within a L2TPv3 Tunnel by using a set of
      {{object|Filter}} objects to determine the treatment of
      the packet.";
      leaf TunnelNumberOfEntries {
        config false;
        description
        "{{numentries}}";
        type uint32;
      }
      leaf FilterNumberOfEntries {
        config false;
        description
        "{{numentries}}";
        type uint32;
      }
      list Tunnel {
        key "Alias";
        config true;
        description
        "A {{object}} object has one or more
        {{object|Interface}} objects that further define the
        sessions or flows within the tunnel.";
        leaf Enable {
          config true;
          description
          "Enables or disables the tunnel.";
          type boolean;
        }
        leaf Status {
          config false;
          description
          "The current operational state of the tunnel.";
          type enumeration {
            enum "Disabled";
            enum "Enabled";
            enum "Error";
          }
        }
        leaf Alias {
          config true;
          description
          "{{datatype|expand}}";
          type Alias;
        }
        leaf-list RemoteEndpoints {
          config true;
          description
          "If more than one name/address is supplied, they will
          be tried in turn, i.e.  they are in decreasing order
          of precedence.";
          type string {
            length "0..256";
          }
        }
        leaf KeepAlivePolicy {
          config true;
          description
          "The mechanism used to keep the tunnel from timing out
          at the {{param|ConnectedRemoteEndpoint}}.";
          type enumeration {
            enum "ICMP" {
              description
              "The version of the ICMP packet used for this
              {{param}} is based on the value of the
              {{param|DeliveryHeaderProtocol}} parameter
              (Either ICMP for IPv4 or ICMPv6 for IPv6).";
            }
            enum "None";
          }
          default "None";
        }
        leaf KeepAliveTimeout {
          config true;
          description
          "The tunnel keepalive timeout in {{units}}.";
          type uint32;
          default "10";
        }
        leaf KeepAliveThreshold {
          config true;
          description
          "Number of KeepAlive messages unacknowledged by the
          {{param|ConnectedRemoteEndpoint}} before the
          {{object}} is perceived failed.";
          type uint32;
          default "3";
        }
        leaf DeliveryHeaderProtocol {
          config true;
          description
          "The protocol used for the delivery header.";
          type enumeration {
            enum "IPv4";
            enum "IPv6";
          }
        }
        leaf DefaultDSCPMark {
          config true;
          description
          "If the specified entries in the {{object|#.Filter}}
          table do not match this {{object}} object or an
          instance of the {{object|Interface}} object for this
          {{object}} object, then the value of this parameter
          is applied to the delivery header of the packets in
          this {{object}}.";
          type uint32;
          default "0";
        }
        leaf TunnelEncapsulation {
          config true;
          description
          "The protocol that this {{object}} will be
          encapsulated";
          type enumeration {
            enum "IP";
            enum "UDP";
          }
          default "IP";
        }
        leaf ConnectedRemoteEndpoint {
          config false;
          description
          "The Fully Qualified Domain Name (FQDN) name or IP
          address of the connected remote L2TPv3 tunnel
          endpoint.";
          type string {
            length "0..256";
          }
        }
        leaf InterfaceNumberOfEntries {
          config false;
          description
          "{{numentries}}";
          type uint32;
        }
        container UDP {
          description
          "This {{object}} provides the parameters when the
          value of the
          {{param|##.Tunnel.{i}.TunnelEncapsulation}} parameter
          is {{enum|UDP|##.Tunnel.{i}.TunnelEncapsulation}}.";
          leaf SourcePort {
            config true;
            description
            "The source (local) port used to transmit PDUs.  A
            value of 0 indicates that the port selection is
            performed by the device.";
            type uint32 {
              range "min..65535";
            }
            default "1701";
          }
          leaf RemotePort {
            config true;
            description
            "The remote port used to by the remote endpoint to
            transmit PDUs.";
            type uint32 {
              range "min..65535";
            }
            default "1701";
          }
          leaf EnableChecksum {
            config true;
            description
            "Enables or disables checksum processing.";
            type boolean;
            default "false";
          }
        }
        container Stats {
          description
          "The device MUST reset the tunnel's Stats parameters
          (unless otherwise stated in individual object or
          parameter descriptions) either when the tunnel
          becomes operationally down due to a previous
          administrative down (i.e., Status parameter
          transitions to a disabled state after the tunnel has
          been disabled) or when the tunnel becomes
          administratively up (i.e.  the Enable parameter
          transitioned from {{false}} to {{true}}).";
          leaf KeepAliveSent {
            config false;
            description
            "The total number of KeepAlive {{units}} sent out
            the tunnel.";
            type yang:counter32;
          }
          leaf KeepAliveReceived {
            config false;
            description
            "The total number of KeepAlive {{units}} received by
            the tunnel.";
            type yang:counter32;
          }
          leaf BytesSent {
            config false;
            description
            "The total number of {{units}} sent by the tunnel.";
            type yang:counter32;
          }
          leaf BytesReceived {
            config false;
            description
            "The total number of {{units}} received by the
            tunnel.";
            type yang:counter32;
          }
          leaf PacketsSent {
            config false;
            description
            "The total number of {{units}} sent by the tunnel.";
            type yang:counter32;
          }
          leaf PacketsReceived {
            config false;
            description
            "The total number of {{units}} received by the
            tunnel.";
            type yang:counter32;
          }
          leaf ErrorsSent {
            config false;
            description
            "The total number of {{units}} discarded by the
            tunnel due to any error.  This can include packets
            dropped due to a lack of transmit buffers.";
            type yang:counter32;
          }
          leaf ErrorsReceived {
            config false;
            description
            "The total number of {{units}} received by the
            tunnel that contained errors preventing them from
            being delivered to a higher-layer protocol.";
            type yang:counter32;
          }
        }
        list Interface {
          key "Name";
          unique "Alias";
          config true;
          description
          "In addition the {{object}} object represents the
          entry point and exit point of the tunnel in relation
          to the LAN interface.";
          leaf Enable {
            config true;
            description
            "This parameter is based on ''ifAdminStatus'' from
            {{bibref|RFC2863}}.";
            type boolean;
          }
          leaf Status {
            config false;
            description
            "This parameter is based on ''ifOperStatus'' from
            {{bibref|RFC2863}}.";
            type enumeration {
              enum "Up";
              enum "Down";
              enum "Unknown";
              enum "Dormant";
              enum "NotPresent";
              enum "LowerLayerDown";
              enum "Error";
            }
          }
          leaf Alias {
            config true;
            description
            "{{datatype|expand}}";
            type Alias;
          }
          leaf Name {
            config true;
            description
            "The textual name of the interface as assigned by
            the CPE.";
            type string {
              length "0..64";
            }
          }
          leaf LastChange {
            config false;
            description
            "The accumulated time in {{units}} since the
            interface entered its current operational state.";
            type uint32;
          }
          leaf-list LowerLayers {
            config true;
            description
            "{{list}} {{reference|an interface object that is
            stacked immediately below this interface object}}
            See {{bibref|TR-181i2|Section 4.2.1}}.";
            type string;
          }
          leaf SessionID {
            config true;
            description
            "A Session ID with a value of -1 indicates that he
            CPE is to generate the session ids for this
            {{object}} instance.";
            type int32 {
              range "-1|1..65535";
            }
            default "1";
          }
          leaf CookiePolicy {
            config true;
            description
            "The policy that defines how the Cookie is handled
            in this {{object}} instance.";
            type enumeration {
              enum "Disabled" {
                description
                "The device does not perform Cooking processing.";
              }
              enum "Configured" {
                description
                "The value of the {{param|Cookie}} parameter is
                transmitted in the L2TPv3 header.";
              }
              enum "Generated" {
                description
                "The device generates the value of the Cookie
                transmitted in the L2TPv3 header.";
              }
            }
            default "Configured";
          }
          leaf Cookie {
            config true;
            description
            "The Cookie transmitted in the L2TPv3 header.  The
            default is to set the Cookie to the device's MAC
            address that is encoded in the low order 6 bytes.";
            type uint64;
          }
          container Stats {
            description
            "The device MUST reset the interface's Stats
            parameters (unless otherwise stated in individual
            object or parameter descriptions) either when the
            interface becomes operationally down due to a
            previous administrative down (i.e., the interface's
            Status parameter transitions to a down state after
            the interface has been disabled) or when the
            interface becomes administratively up (i.e.  the
            Enable parameter transitioned from {{false}} to
            {{true}}).";
            leaf BytesSent {
              config false;
              description
              "The total number of {{units}} sent by this
              interface.";
              type yang:counter32;
            }
            leaf BytesReceived {
              config false;
              description
              "The total number of {{units}} received by this
              interface.";
              type yang:counter32;
            }
            leaf PacketsSent {
              config false;
              description
              "The total number of {{units}} sent by this
              interface.";
              type yang:counter32;
            }
            leaf PacketsReceived {
              config false;
              description
              "The total number of {{units}} received by this
              interface.";
              type yang:counter32;
            }
            leaf ErrorsSent {
              config false;
              description
              "The total number of {{units}} discarded by this
              interface due to any error.  This can include
              packets dropped due to a lack of transmit
              buffers.";
              type yang:counter32;
            }
            leaf ErrorsReceived {
              config false;
              description
              "The total number of {{units}} received by this
              interface that contained errors preventing them
              from being delivered to a higher-layer protocol.";
              type yang:counter32;
            }
            leaf DiscardChecksumReceived {
              config false;
              description
              "The total number of {{units}} received by the
              tunnel interface that are discarded because of
              Checksum errors.";
              type yang:counter32;
            }
            leaf DiscardSequenceNumberReceived {
              config false;
              description
              "The total number of {{units}} received by the
              tunnel interface that are discarded because of
              Sequence Number errors.";
              type yang:counter32;
            }
          }
        }
      }
      list Filter {
        key "Alias";
        config true;
        description
        "For enabled table entries, if {{param|Interface}} is
        not a valid reference and {{param|AllInterfaces}} is
        {{false}}, then the table entry is inoperable and the
        CPE MUST set {{param|Status}} to
        {{enum|Error_Misconfigured|Status}}.";
        leaf Enable {
          config true;
          description
          "Enables or disables this filter.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Order {
          config true;
          description
          "The value of {{param}} on creation of a {{object}}
          table entry MUST be one greater than the largest
          current value (initially assigned the lowest
          precedence).";
          type uint32 {
            range "1..max";
          }
        }
        leaf Alias {
          config true;
          description
          "{{datatype|expand}}";
          type Alias;
        }
        leaf Interface {
          config true;
          description
          "Filter criterion.  {{reference}}";
          type string {
            length "0..256";
          }
        }
        leaf AllInterfaces {
          config true;
          description
          "Filter criterion.  This specifies that all ingress
          L2TPv3 tunnel interfaces are associated with the
          entry.  If {{true}}, the value of {{param|Interface}}
          is ignored since all ingress L2TPv3 tunnel interfaces
          are indicated.";
          type boolean;
          default "false";
        }
        leaf VLANIDCheck {
          config true;
          description
          "Current outer Ethernet VLAN ID as defined in 802.1Q.
          A value of -1 indicates this criterion is not used
          for filtering.";
          type int32 {
            range "-1..max";
          }
          default "-1";
        }
        leaf VLANIDExclude {
          config true;
          description
          "If {{true}}, the filter includes all packets except
          those that match the {{param|VLANIDCheck}} entry, if
          specified.";
          type boolean;
          default "false";
        }
        leaf DSCPMarkPolicy {
          config true;
          description
          "* A value of -2 indicates automatic marking of DSCP.";
          type int32 {
            range "-2..63";
          }
        }
      }
    }
    container VXLAN {
      description
      "This object also provides a means to treat packets that
      are encapsulated within a VXLAN Tunnel by using a set of
      {{object|Filter}} objects to determine the treatment of
      the packet.";
      leaf TunnelNumberOfEntries {
        config false;
        description
        "{{numentries}}";
        type uint32;
      }
      leaf FilterNumberOfEntries {
        config false;
        description
        "{{numentries}}";
        type uint32;
      }
      list Tunnel {
        key "Alias";
        config true;
        description
        "A {{object}} object has one or more
        {{object|Interface}} objects that further define the
        sessions or flows within the tunnel.";
        leaf Enable {
          config true;
          description
          "Enables or disables the tunnel.";
          type boolean;
        }
        leaf Status {
          config false;
          description
          "The current operational state of the tunnel.";
          type enumeration {
            enum "Disabled";
            enum "Enabled";
            enum "Error";
          }
        }
        leaf Alias {
          config true;
          description
          "{{datatype|expand}}";
          type Alias;
        }
        leaf-list RemoteEndpoints {
          config true;
          description
          "If more than one name/address is supplied, they will
          be tried in turn, i.e.  they are in decreasing order
          of precedence.";
          type string {
            length "0..256";
          }
        }
        leaf KeepAlivePolicy {
          config true;
          description
          "The mechanism used to keep the tunnel from timing out
          at the {{param|ConnectedRemoteEndpoint}}.";
          type enumeration {
            enum "ICMP" {
              description
              "The version of the ICMP packet used for this
              {{param}} is based on the value of the
              {{param|DeliveryHeaderProtocol}} parameter
              (Either ICMP for IPv4 or ICMPv6 for IPv6).";
            }
            enum "None";
          }
          default "None";
        }
        leaf KeepAliveTimeout {
          config true;
          description
          "The tunnel keepalive timeout in {{units}}.";
          type uint32;
          default "10";
        }
        leaf KeepAliveThreshold {
          config true;
          description
          "Number of KeepAlive messages unacknowledged by the
          {{param|ConnectedRemoteEndpoint}} before the
          {{object}} is perceived failed.";
          type uint32;
          default "3";
        }
        leaf DeliveryHeaderProtocol {
          config true;
          description
          "The protocol used for the delivery header.";
          type enumeration {
            enum "IPv4";
            enum "IPv6";
          }
        }
        leaf DefaultDSCPMark {
          config true;
          description
          "If the specified entries in the {{object|#.Filter}}
          table do not match this {{object}} object or an
          instance of the {{object|Interface}} object for this
          {{object}} object, then the value of this parameter
          is applied to the delivery header of the packets in
          this {{object}}.";
          type uint32;
          default "0";
        }
        leaf ConnectedRemoteEndpoint {
          config false;
          description
          "The Fully Qualified Domain Name (FQDN) name or IP
          address of the connected remote VXLAN tunnel
          endpoint.";
          type string {
            length "0..256";
          }
        }
        leaf InterfaceNumberOfEntries {
          config false;
          description
          "{{numentries}}";
          type uint32;
        }
        leaf SourcePort {
          config true;
          description
          "The source (local) port used to transmit PDUs.  A
          value of 0 indicates that the port selection is
          performed by the device.  In such case, it is
          recommended that the UDP source port number be
          calculated using a hash of fields from the inner
          packet and that it is in the dynamic/private port
          range 49152-65535.";
          type uint32 {
            range "min..65535";
          }
          default "0";
        }
        leaf RemotePort {
          config true;
          description
          "The remote port used to by the remote endpoint to
          transmit PDUs.  The well-known port allocated by IANA
          is 4789, but it should be configurable.";
          type uint32 {
            range "min..65535";
          }
          default "4789";
        }
        container Stats {
          description
          "The device MUST reset the tunnel's Stats parameters
          (unless otherwise stated in individual object or
          parameter descriptions) either when the tunnel
          becomes operationally down due to a previous
          administrative down (i.e., Status parameter
          transitions to a disabled state after the tunnel has
          been disabled) or when the tunnel becomes
          administratively up (i.e.  the Enable parameter
          transitioned from {{false}} to {{true}}).";
          leaf KeepAliveSent {
            config false;
            description
            "The total number of KeepAlive {{units}} sent out
            the tunnel.";
            type yang:counter32;
          }
          leaf KeepAliveReceived {
            config false;
            description
            "The total number of KeepAlive {{units}} received by
            the tunnel.";
            type yang:counter32;
          }
          leaf BytesSent {
            config false;
            description
            "The total number of {{units}} sent by the tunnel.";
            type yang:counter32;
          }
          leaf BytesReceived {
            config false;
            description
            "The total number of {{units}} received by the
            tunnel.";
            type yang:counter32;
          }
          leaf PacketsSent {
            config false;
            description
            "The total number of {{units}} sent by the tunnel.";
            type yang:counter32;
          }
          leaf PacketsReceived {
            config false;
            description
            "The total number of {{units}} received by the
            tunnel.";
            type yang:counter32;
          }
          leaf ErrorsSent {
            config false;
            description
            "The total number of {{units}} discarded by the
            tunnel due to any error.  This can include packets
            dropped due to a lack of transmit buffers.";
            type yang:counter32;
          }
          leaf ErrorsReceived {
            config false;
            description
            "The total number of {{units}} received by the
            tunnel that contained errors preventing them from
            being delivered to a higher-layer protocol.";
            type yang:counter32;
          }
        }
        list Interface {
          key "Name";
          unique "Alias";
          config true;
          description
          "In addition the {{object}} object represents the
          entry point and exit point of the tunnel in relation
          to the LAN interface.";
          leaf Enable {
            config true;
            description
            "This parameter is based on ''ifAdminStatus'' from
            {{bibref|RFC2863}}.";
            type boolean;
          }
          leaf Status {
            config false;
            description
            "This parameter is based on ''ifOperStatus'' from
            {{bibref|RFC2863}}.";
            type enumeration {
              enum "Up";
              enum "Down";
              enum "Unknown";
              enum "Dormant";
              enum "NotPresent";
              enum "LowerLayerDown";
              enum "Error";
            }
          }
          leaf Alias {
            config true;
            description
            "{{datatype|expand}}";
            type Alias;
          }
          leaf Name {
            config true;
            description
            "The textual name of the interface as assigned by
            the CPE.";
            type string {
              length "0..64";
            }
          }
          leaf LastChange {
            config false;
            description
            "The accumulated time in {{units}} since the
            interface entered its current operational state.";
            type uint32;
          }
          leaf-list LowerLayers {
            config true;
            description
            "{{list}} {{reference|an interface object that is
            stacked immediately below this interface object}}
            See {{bibref|TR-181i2|Section 4.2.1}}.";
            type string;
          }
          leaf VNI {
            config true;
            description
            "A VNI with a value of -1 indicates that the CPE is
            to generate the VNI for this {{object}} instance.";
            type int32 {
              range "-1|0..16777215";
            }
            default "1";
          }
          container Stats {
            description
            "The device MUST reset the interface's Stats
            parameters (unless otherwise stated in individual
            object or parameter descriptions) either when the
            interface becomes operationally down due to a
            previous administrative down (i.e., the interface's
            Status parameter transitions to a down state after
            the interface has been disabled) or when the
            interface becomes administratively up (i.e.  the
            Enable parameter transitioned from {{false}} to
            {{true}}).";
            leaf BytesSent {
              config false;
              description
              "The total number of {{units}} sent by this
              interface.";
              type yang:counter32;
            }
            leaf BytesReceived {
              config false;
              description
              "The total number of {{units}} received by this
              interface.";
              type yang:counter32;
            }
            leaf PacketsSent {
              config false;
              description
              "The total number of {{units}} sent by this
              interface.";
              type yang:counter32;
            }
            leaf PacketsReceived {
              config false;
              description
              "The total number of {{units}} received by this
              interface.";
              type yang:counter32;
            }
            leaf ErrorsSent {
              config false;
              description
              "The total number of {{units}} discarded by this
              interface due to any error.  This can include
              packets dropped due to a lack of transmit
              buffers.";
              type yang:counter32;
            }
            leaf ErrorsReceived {
              config false;
              description
              "The total number of {{units}} received by this
              interface that contained errors preventing them
              from being delivered to a higher-layer protocol.";
              type yang:counter32;
            }
            leaf DiscardChecksumReceived {
              config false;
              description
              "The total number of {{units}} received by the
              tunnel interface that are discarded because of
              Checksum errors.";
              type yang:counter32;
            }
            leaf DiscardSequenceNumberReceived {
              config false;
              description
              "The total number of {{units}} received by the
              tunnel interface that are discarded because of
              Sequence Number errors.";
              type yang:counter32;
            }
          }
        }
      }
      list Filter {
        key "Alias";
        config true;
        description
        "For enabled table entries, if {{param|Interface}} is
        not a valid reference and {{param|AllInterfaces}} is
        {{false}}, then the table entry is inoperable and the
        CPE MUST set {{param|Status}} to
        {{enum|Error_Misconfigured|Status}}.";
        leaf Enable {
          config true;
          description
          "Enables or disables this filter.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Order {
          config true;
          description
          "The value of {{param}} on creation of a {{object}}
          table entry MUST be one greater than the largest
          current value (initially assigned the lowest
          precedence).";
          type uint32 {
            range "1..max";
          }
        }
        leaf Alias {
          config true;
          description
          "{{datatype|expand}}";
          type Alias;
        }
        leaf Interface {
          config true;
          description
          "Filter criterion.  {{reference}}";
          type string {
            length "0..256";
          }
        }
        leaf AllInterfaces {
          config true;
          description
          "Filter criterion.  This specifies that all ingress
          VXLAN tunnel interfaces are associated with the
          entry.  If {{true}}, the value of {{param|Interface}}
          is ignored since all ingress VXLAN tunnel interfaces
          are indicated.";
          type boolean;
          default "false";
        }
        leaf VLANIDCheck {
          config true;
          description
          "Current outer Ethernet VLAN ID as defined in 802.1Q.
          A value of -1 indicates this criterion is not used
          for filtering.";
          type int32 {
            range "-1..max";
          }
          default "-1";
        }
        leaf VLANIDExclude {
          config true;
          description
          "If {{true}}, the filter includes all packets except
          those that match the {{param|VLANIDCheck}} entry, if
          specified.";
          type boolean;
          default "false";
        }
        leaf DSCPMarkPolicy {
          config true;
          description
          "* A value of -2 indicates automatic marking of DSCP.";
          type int32 {
            range "-2..63";
          }
        }
      }
    }
    container MAP {
      description
      "See the MAP Theory of Operation
      {{bibref|TR-181i2a8|Appendix XV}} for a description of
      the working of this MAP data model.";
      leaf Enable {
        config true;
        description
        "Enables or disables MAP.";
        type boolean;
      }
      leaf DomainNumberOfEntries {
        config false;
        description
        "{{numentries}}";
        type uint32;
      }
      list Domain {
        key "WANInterface IPv6Prefix";
        unique "Alias";
        config true;
        description
        "Note: The {{object}} table includes unique key
        parameters that are strong references.  If a strongly
        referenced object is deleted, the CPE will set the
        referencing parameter to {{empty}}. However, doing so
        under these circumstances might cause the updated
        {{object}} row to then violate the table's unique key
        constraint; if this occurs, the CPE MUST set
        {{param|Status}} to {{enum|Error_Misconfigured|Status}}
        and disable the offending {{object}} row.";
        leaf Enable {
          config true;
          description
          "Enables or disables the MAP domain.";
          type boolean;
          default "false";
        }
        leaf Status {
          config false;
          description
          "The {{enum|Error_Misconfigured}} value indicates that
          a necessary configuration value is undefined or
          invalid.";
          type enumeration {
            enum "Disabled";
            enum "Enabled";
            enum "Error_Misconfigured";
            enum "Error";
          }
        }
        leaf Alias {
          config true;
          description
          "{{datatype|expand}}";
          type Alias;
        }
        leaf TransportMode {
          config true;
          description
          "Corresponds to the {{bibref|RFC7598}}
          ''S46_CONT_MAPE'' and ''S46_CONT_MAPT'' container
          options.";
          type enumeration {
            enum "Encapsulation" {
              description
              "MAP-E {{bibref|RFC7597}}";
            }
            enum "Translation" {
              description
              "MAP-T {{bibref|RFC7599}}";
            }
          }
          default "Translation";
        }
        leaf WANInterface {
          config true;
          description
          "The ''MAP IPv6 address'' is derived from the
          ''End-user IPv6 prefix'' and is one of this IP
          interface's IP addresses, with an
          {{param|##.IP.Interface.{i}.IPv6Address.{i}.Origin}}
          of
          {{enum|MAP|##.IP.Interface.{i}.IPv6Address.{i}.Origin}}.";
          type string;
        }
        leaf IPv6Prefix {
          config true;
          description
          "If the ACS configures this prefix directly, the CPE
          MUST use the ACS-configured prefix.  Otherwise, the
          CPE MUST select one of {{param|WANInterface}}'s
          prefixes; the selected prefix will typically have
          {{param|##.IP.Interface.{i}.IPv6Prefix.{i}.Origin}} =
          {{enum|PrefixDelegation|##.IP.Interface.{i}.IPv6Prefix.{i}.Origin}}.";
          type string;
        }
        leaf BRIPv6Prefix {
          config true;
          description
          "Note: There will be a corresponding
          {{object|.Routing.Router.{i}.IPv4Forwarding}} default
          rule.";
          type inet:ipv6-prefix;
        }
        leaf DSCPMarkPolicy {
          config true;
          description
          "* A value of -2 indicates automatic marking of DSCP.";
          type int32 {
            range "-2..63";
          }
        }
        leaf PSIDOffset {
          config true;
          description
          "This parameter is DEPRECATED because details changed
          between drafting this data model and the RFC being
          published.  This parameter has been moved to the
          proper location within the {{object|Rule.{i}.}}
          object.";
          type uint32 {
            range "0..15";
          }
          default "6";
        }
        leaf PSIDLength {
          config true;
          description
          "This parameter is DEPRECATED because details changed
          between drafting this data model and the RFC being
          published.  This parameter has been moved to the
          proper location within the {{object|Rule.{i}.}}
          object.";
          type uint32 {
            range "0..16";
          }
          default "0";
        }
        leaf PSID {
          config true;
          description
          "This parameter is DEPRECATED because details changed
          between drafting this data model and the RFC being
          published.  This parameter has been moved to the
          proper location within the {{object|Rule.{i}.}}
          object.";
          type uint32 {
            range "0..65535";
          }
          default "0";
        }
        leaf IncludeSystemPorts {
          config true;
          description
          "This parameter is related to {{bibref|RFC7597}}'s
          ''N'', which is defined as ''the number of ports
          (e.g., 1024) excluded from the lower end of the
          range''.  The parameter is relevant only when
          {{param|PSIDOffset}} is 0; {{false}} corresponds to
          ''N=1024'' and {{true}} corresponds to ''N=0''.";
          type boolean;
          default "false";
        }
        leaf RuleNumberOfEntries {
          config false;
          description
          "{{numentries}}";
          type uint32;
        }
        list Rule {
          key "IPv6Prefix";
          unique "Alias";
          unique "IPv4Prefix";
          config true;
          description
          "The MAP domain's Mapping Rules {{bibref|RFC7597}}.
          The rule with the longest match between its
          {{param|IPv6Prefix}} and the end-user
          {{param|#.IPv6Prefix}} is the Basic Mapping Rule
          (BMR). Any of the rules (including the BMR) can be a
          Forwarding Mapping Rule.";
          leaf Enable {
            config true;
            description
            "Enable or disable this {{object}} instance.";
            type boolean;
            default "false";
          }
          leaf Status {
            config false;
            description
            "The {{enum|Error}} value MAY be used by the CPE to
            indicate a locally defined error condition.";
            type enumeration {
              enum "Disabled";
              enum "Enabled";
              enum "Error";
            }
            default "Disabled";
          }
          leaf Alias {
            config true;
            description
            "{{datatype|expand}}";
            type Alias;
          }
          leaf Origin {
            config false;
            description
            "If the CPE supports MAP configuration via both
            DHCPv6 and CWMP, it is up to the implementation to
            determine how the two mechanisms will interact.";
            type enumeration {
              enum "DHCPv6" {
                description
                "Created via a {{bibref|RFC7598}} ''S46_RULE''
                option.";
              }
              enum "Static" {
                description
                "Present in the factory default configuration,
                created by the ACS, or created by some other
                management entity (e.g.  via a GUI)";
              }
            }
            default "Static";
          }
          leaf IPv6Prefix {
            config true;
            description
            "Corresponds to the {{bibref|RFC7598}} ''S46_RULE''
            option's ''ipv6-prefix'' field.";
            type inet:ipv6-prefix;
          }
          leaf IPv4Prefix {
            config true;
            description
            "Corresponds to the {{bibref|RFC7598}} ''S46_RULE''
            option's ''ipv4-prefix'' field.";
            type inet:ipv4-prefix;
          }
          leaf EABitsLength {
            config true;
            description
            "Corresponds to the {{bibref|RFC7598}} ''S46_RULE''
            option's ''ea-len'' field.";
            type uint32 {
              range "0..48";
            }
            default "0";
          }
          leaf IsFMR {
            config true;
            description
            "Corresponds to the {{bibref|RFC7598}} ''S46_RULE''
            option's ''flags'' field's ''F-Flag''.";
            type boolean;
            default "false";
          }
          leaf PSIDOffset {
            config true;
            description
            "Corresponds to the {{bibref|RFC7598}}
            ''S46_PORTPARAMS'' (Port Parameters) option's
            ''offset'' field.";
            type uint32 {
              range "0..15";
            }
            default "6";
          }
          leaf PSIDLength {
            config true;
            description
            "Corresponds to the {{bibref|RFC7598}}
            ''S46_PORTPARAMS'' (Port Parameters) option's
            ''PSID-len'' field.";
            type uint32 {
              range "0..16";
            }
            default "0";
          }
          leaf PSID {
            config true;
            description
            "Corresponds to the {{bibref|RFC7598}}
            ''S46_PORTPARAMS'' (Port Parameters) option's
            ''PSID'' field.";
            type uint32 {
              range "0..65535";
            }
            default "0";
          }
        }
        container Interface {
          description
          "MAP interface (a stackable interface object as
          described in {{bibref|TR-181i2|Section 4.2}}).  This
          models the LAN side MAP domain interface.";
          leaf Enable {
            config true;
            description
            "This parameter is based on ''ifAdminStatus'' from
            {{bibref|RFC2863}}.";
            type boolean;
            default "false";
          }
          leaf Status {
            config false;
            description
            "This parameter is based on ''ifOperStatus'' from
            {{bibref|RFC2863}}.";
            type enumeration {
              enum "Up";
              enum "Down";
              enum "Unknown";
              enum "Dormant";
              enum "NotPresent";
              enum "LowerLayerDown";
              enum "Error";
            }
          }
          leaf Alias {
            config true;
            description
            "{{datatype|expand}}";
            type Alias;
          }
          leaf Name {
            config false;
            description
            "The textual name of the interface as assigned by
            the CPE.";
            type string {
              length "0..64";
            }
          }
          leaf LastChange {
            config false;
            description
            "The accumulated time in {{units}} since the
            interface entered its current operational state.";
            type uint32;
          }
          leaf-list LowerLayers {
            config true;
            description
            "Note: Since this interface object is a MAP domain
            interface, it is expected that {{param}} will not
            be used.";
            type string;
          }
          container Stats {
            description
            "The CPE MUST reset the interface's Stats parameters
            (unless otherwise stated in individual object or
            parameter descriptions) either when the interface
            becomes operationally down due to a previous
            administrative down (i.e.  the interface's
            {{param|#.Status}} parameter transitions to a down
            state after the interface is disabled) or when the
            interface becomes administratively up (i.e.  the
            interface's {{param|#.Enable}} parameter
            transitions from {{false}} to {{true}}).
            Administrative and operational interface status is
            discussed in {{bibref|TR-181i2|section 4.2.2}}.";
            leaf BytesSent {
              config false;
              description
              "The total number of bytes transmitted out of the
              interface, including framing characters.";
              type yang:counter32;
            }
            leaf BytesReceived {
              config false;
              description
              "The total number of bytes received on the
              interface, including framing characters.";
              type yang:counter32;
            }
            leaf PacketsSent {
              config false;
              description
              "The total number of packets transmitted out of
              the interface.";
              type yang:counter32;
            }
            leaf PacketsReceived {
              config false;
              description
              "The total number of packets received on the
              interface.";
              type yang:counter32;
            }
            leaf ErrorsSent {
              config false;
              description
              "The total number of outbound packets that could
              not be transmitted because of errors.";
              type yang:counter32;
            }
            leaf ErrorsReceived {
              config false;
              description
              "The total number of inbound packets that
              contained errors preventing them from being
              delivered to a higher-layer protocol.";
              type yang:counter32;
            }
            leaf UnicastPacketsSent {
              config false;
              description
              "The total number of packets requested for
              transmission which were not addressed to a
              multicast or broadcast address at this layer,
              including those that were discarded or not sent.";
              type yang:counter32;
            }
            leaf UnicastPacketsReceived {
              config false;
              description
              "The total number of received packets, delivered
              by this layer to a higher layer, which were not
              addressed to a multicast or broadcast address at
              this layer.";
              type yang:counter32;
            }
            leaf DiscardPacketsSent {
              config false;
              description
              "The total number of outbound packets which were
              chosen to be discarded even though no errors had
              been detected to prevent their being transmitted.
              One possible reason for discarding such a packet
              could be to free up buffer space.";
              type yang:counter32;
            }
            leaf DiscardPacketsReceived {
              config false;
              description
              "The total number of inbound packets which were
              chosen to be discarded even though no errors had
              been detected to  prevent their being delivered.
              One possible reason for discarding such a packet
              could be to free up buffer space.";
              type yang:counter32;
            }
            leaf MulticastPacketsSent {
              config false;
              description
              "The total number of packets that higher-level
              protocols requested for transmission and which
              were addressed to a multicast address at this
              layer, including those that were discarded or not
              sent.";
              type yang:counter32;
            }
            leaf MulticastPacketsReceived {
              config false;
              description
              "The total number of received packets, delivered
              by this layer to a higher layer, which were
              addressed to a multicast address at this layer.";
              type yang:counter32;
            }
            leaf BroadcastPacketsSent {
              config false;
              description
              "Note that IPv6 does not define broadcast
              addresses, so IPv6 packets will never cause this
              counter to increment.";
              type yang:counter32;
            }
            leaf BroadcastPacketsReceived {
              config false;
              description
              "Note that IPv6 does not define broadcast
              addresses, so IPv6 packets will never cause this
              counter to increment.";
              type yang:counter32;
            }
            leaf UnknownProtoPacketsReceived {
              config false;
              description
              "The total number of packets received via the
              interface which were discarded because of an
              unknown or unsupported  protocol.";
              type yang:counter32;
            }
          }
        }
      }
    }
    container CaptivePortal {
      description
      "When the captive portal is enabled, upstream HTTP (port
      80) traffic MUST be permitted only to destinations listed
      in the {{param|AllowedList}}; traffic to all other
      destinations MUST be redirected to the {{param|URL}}.";
      leaf Enable {
        config true;
        description
        "Enables or disables the captive portal.";
        type boolean;
      }
      leaf Status {
        config false;
        description
        "The {{enum|Error}} value MAY be used by the CPE to
        indicate a locally defined error condition.";
        type enumeration {
          enum "Disabled";
          enum "Enabled";
          enum "Error_URLEmpty" {
            description
            "{{param|URL}} is {{empty}}";
          }
          enum "Error";
        }
      }
      leaf-list AllowedList {
        config true;
        description
        "* 2001:edff:fe6a:f76::/64 represents the IPv6 addresses
        from 2001:edff:fe6a:f76:0:0:0:0 to
        2001:edff:fe6a:f76:ffff:ffff:ffff:ffff.";
        type string;
      }
      leaf URL {
        config true;
        description
        "The CPE MUST permit the captive portal URL to be set to
        {{empty}}, which has the effect of disabling the
        captive portal (if {{param|Enable}} is {{true}} and the
        captive portal URL is {{empty}}, {{param|Status}} MUST
        be {{enum|Error_URLEmpty|Status}}).";
        type string {
          length "0..2000";
        }
      }
    }
    container Routing {
      description
      "Routing object that contains the {{object|Router}} table
      and {{object|RIP}} protocol object.";
      leaf RouterNumberOfEntries {
        config false;
        description
        "{{numentries}}";
        type uint32;
      }
      list Router {
        key "Alias";
        config true;
        description
        "This object allows the handling of the routing and
        forwarding configuration of the device.";
        leaf Enable {
          config true;
          description
          "Enables or disables this ''Router'' entry.";
          type boolean;
          default "false";
        }
        leaf Status {
          config false;
          description
          "The {{enum|Error}} value MAY be used by the CPE to
          indicate a locally defined error condition.";
          type enumeration {
            enum "Disabled";
            enum "Enabled";
            enum "Error";
          }
          default "Disabled";
        }
        leaf Alias {
          config true;
          description
          "{{datatype|expand}}";
          type Alias;
        }
        leaf IPv4ForwardingNumberOfEntries {
          config false;
          description
          "{{numentries}}";
          type uint32;
        }
        leaf IPv6ForwardingNumberOfEntries {
          config false;
          description
          "{{numentries}}";
          type uint32;
        }
        list IPv4Forwarding {
          key "DestIPAddress DestSubnetMask ForwardingPolicy GatewayIPAddress Interface ForwardingMetric";
          unique "Alias";
          config true;
          description
          "Note: The {{object}} table includes a unique key
          parameter that is a strong reference.  If a strongly
          referenced object is deleted, the CPE will set the
          referencing parameter to {{empty}}. However, doing so
          under these circumstances might cause the updated
          {{object}} row to then violate the table's unique key
          constraint; if this occurs, the CPE MUST disable the
          offending {{object}} row.";
          leaf Enable {
            config true;
            description
            "Enables or disables the forwarding entry.  On
            creation, an entry is disabled by default.";
            type boolean;
            default "false";
          }
          leaf Status {
            config false;
            description
            "The {{enum|Error_Misconfigured}} value indicates
            that a necessary configuration value is undefined
            or invalid.";
            type enumeration {
              enum "Disabled";
              enum "Enabled";
              enum "Error_Misconfigured";
              enum "Error";
            }
            default "Disabled";
          }
          leaf Alias {
            config true;
            description
            "{{datatype|expand}}";
            type Alias;
          }
          leaf StaticRoute {
            config false;
            description
            "If {{true}}, this route is a Static route.";
            type boolean;
            default "true";
          }
          leaf DestIPAddress {
            config true;
            description
            "A Forwarding table entry for which {{param}} and
            {{param|DestSubnetMask}} are both {{empty}} is a
            default route.";
            type inet:ipv4-address;
          }
          leaf DestSubnetMask {
            config true;
            description
            "A Forwarding table entry for which
            {{param|DestIPAddress}} and {{param}} are both
            {{empty}} is a default route.";
            type inet:ipv4-address;
          }
          leaf ForwardingPolicy {
            config true;
            description
            "If specified, this forwarding entry is to apply
            only to traffic associated with the specified
            classes and flows.";
            type int32 {
              range "-1..max";
            }
          }
          leaf GatewayIPAddress {
            config true;
            description
            "If both are configured, {{param}} and
            {{param|Interface}} MUST be consistent with each
            other.";
            type inet:ipv4-address;
          }
          leaf Interface {
            config true;
            description
            "For a route that was configured by setting
            {{param|GatewayIPAddress}} but not {{param}}, read
            access to {{param}} MUST return the full
            hierarchical parameter name for the routes egress
            interface.";
            type string {
              length "0..256";
            }
          }
          leaf Origin {
            config false;
            description
            "Protocol via which the IPv4 forwarding rule was
            learned.  {{enum}}";
            type enumeration {
              enum "DHCPv4";
              enum "OSPF";
              enum "IPCP";
              enum "RIP";
              enum "Static" {
                description
                "For example, present in the factory default
                configuration, created by the ACS, or created
                by some other management entity (e.g.  via a
                GUI).";
              }
            }
            default "Static";
          }
          leaf ForwardingMetric {
            config true;
            description
            "Forwarding metric.  A value of -1 indicates this
            metric is not used.";
            type int32 {
              range "-1..max";
            }
          }
        }
        list IPv6Forwarding {
          key "DestIPPrefix ForwardingPolicy NextHop Interface ForwardingMetric";
          unique "Alias";
          config true;
          description
          "This object is based on ''inetCidrRouteTable'' from
          {{bibref|RFC4292}}.";
          leaf Enable {
            config true;
            description
            "Enables or disables this {{object}} entry.";
            type boolean;
            default "false";
          }
          leaf Status {
            config false;
            description
            "The {{enum|Error}} value MAY be used by the CPE to
            indicate a locally defined error condition.";
            type enumeration {
              enum "Disabled";
              enum "Enabled";
              enum "Error_Misconfigured";
              enum "Error";
            }
            default "Disabled";
          }
          leaf Alias {
            config true;
            description
            "{{datatype|expand}}";
            type Alias;
          }
          leaf DestIPPrefix {
            config true;
            description
            "Routes with a 128-bit prefix length (/128) are host
            routes for a specific IPv6 destination, e.g.
            2001:db8:28:2:713e:a426:d167:37ab/128.";
            type inet:ipv6-prefix;
          }
          leaf ForwardingPolicy {
            config true;
            description
            "If specified, this forwarding entry is to apply
            only to traffic associated with the specified
            classes and flows.";
            type int32 {
              range "-1..max";
            }
          }
          leaf NextHop {
            config true;
            description
            "If both are configured, {{param}} and
            {{param|Interface}} MUST be consistent with each
            other.";
            type inet:ipv6-address;
          }
          leaf Interface {
            config true;
            description
            "For a route that was configured by setting
            {{param|NextHop}} but not {{param}}, read access to
            {{param}} MUST return the full hierarchical
            parameter name for the route's egress interface.";
            type string {
              length "0..256";
            }
          }
          leaf Origin {
            config false;
            description
            "Protocol via which the IPv6 forwarding rule was
            learned.  {{enum}}";
            type enumeration {
              enum "DHCPv6";
              enum "OSPF";
              enum "RA" {
                description
                "Router Advertisement Route Information Option
                {{bibref|RFC4191}}.";
              }
              enum "RIPng" {
                description
                "RIPng for IPv6 {{bibref|RFC2080}}";
              }
              enum "Static" {
                description
                "For example, present in the factory default
                configuration, created by the ACS, or created
                by some other management entity (e.g.  via a
                GUI).";
              }
            }
            default "Static";
          }
          leaf ForwardingMetric {
            config true;
            description
            "Forwarding metric.  A value of -1 indicates this
            metric is not used.";
            type int32 {
              range "-1..max";
            }
          }
          leaf ExpirationTime {
            config false;
            description
            "{{param}} is provided by an underlying dynamic
            routing protocol, e.g.  by an {{bibref|RFC4191}}
            route information option.";
            type yang:date-and-time;
            default "9999-12-31T23:59:59Z";
          }
        }
      }
      container RIP {
        description
        "Routing Information Protocol (RIP) object.";
        leaf Enable {
          config true;
          description
          "Enables or disables RIP on the device.";
          type boolean;
        }
        leaf SupportedModes {
          config false;
          description
          "The supported RIP protocol modes.  {{enum}}";
          type enumeration {
            enum "Send";
            enum "Receive";
            enum "Both";
          }
        }
        leaf InterfaceSettingNumberOfEntries {
          config false;
          description
          "{{numentries}}";
          type uint32;
        }
        list InterfaceSetting {
          key "Interface";
          unique "Alias";
          config true;
          description
          "Note: This object only applies to RIP2; i.e.  version
          2 of the RIP protocol is used to accept or send over
          the specified {{param|Interface}}.";
          leaf Enable {
            config true;
            description
            "Enables or disables this entry.";
            type boolean;
            default "false";
          }
          leaf Status {
            config false;
            description
            "The {{enum|Error}} value MAY be used by the CPE to
            indicate a locally defined error condition.";
            type enumeration {
              enum "Disabled";
              enum "Enabled";
              enum "Error_Misconfigured";
              enum "Error";
            }
            default "Disabled";
          }
          leaf Alias {
            config true;
            description
            "{{datatype|expand}}";
            type Alias;
          }
          leaf Interface {
            config true;
            description
            "{{reference}} This is the IP interface associated
            with this {{object}} entry.";
            type string {
              length "0..256";
            }
          }
          leaf AcceptRA {
            config true;
            description
            "When set to {{false}}, RIP route advertisements
            received over {{param|Interface}} are rejected.";
            type boolean;
          }
          leaf SendRA {
            config true;
            description
            "When set to {{false}}, no RIP route advertisements
            will be sent over {{param|Interface}}.";
            type boolean;
          }
        }
      }
      container RouteInformation {
        description
        "Received Router Advertisement (RA) route information
        {{bibref|RFC4191}}.";
        leaf Enable {
          config true;
          description
          "Enables or disables receiving route information from
          the RA.";
          type boolean;
        }
        leaf InterfaceSettingNumberOfEntries {
          config false;
          description
          "{{numentries}}";
          type uint32;
        }
        list InterfaceSetting {
          key "Interface";
          config false;
          description
          "IP Interface RA route information table.  Contains
          received RA route information {{bibref|RFC4191}}. As
          such, the data in this table cannot be modified.";
          leaf Status {
            config false;
            description
            "The {{enum|Error}} value MAY be used by the CPE to
            indicate a locally defined error condition.";
            type enumeration {
              enum "ForwardingEntryCreated";
              enum "NoForwardingEntry";
              enum "Error";
            }
          }
          leaf Interface {
            config false;
            description
            "{{reference}} This is the IP interface associated
            with this {{object}} entry.";
            type string {
              length "0..256";
            }
          }
          leaf SourceRouter {
            config false;
            description
            "IPv6 Address of the router that sent the RA that
            included this route info.";
            type inet:ipv6-address;
          }
          leaf PreferredRouteFlag {
            config false;
            description
            "Note that this is not the Prf flag included in the
            base RA message.  Also see {{bibref|RFC4191|Section
            2.1}} which discusses how this flag is encoded on
            the wire.";
            type enumeration {
              enum "High";
              enum "Medium";
              enum "Low";
            }
          }
          leaf Prefix {
            config false;
            description
            "IPv6 address prefix, as received in an instance of
            the Route Information Option of a RA message.";
            type inet:ipv6-prefix;
          }
          leaf RouteLifetime {
            config false;
            description
            "{{param}} is received in an instance of the Route
            Information Option of a RA message.";
            type yang:date-and-time;
          }
        }
      }
    }
    container NeighborDiscovery {
      description
      "The Neighbor Discovery Protocol (NDP) object
      {{bibref|RFC4861}}.  This object applies only to IPv6.
      It contains an {{object|InterfaceSetting}} table that
      defines the NDP configuration for individual IP
      interfaces.";
      leaf Enable {
        config true;
        description
        "Enables or disables Neighbor Discovery.";
        type boolean;
      }
      leaf InterfaceSettingNumberOfEntries {
        config false;
        description
        "{{numentries}}";
        type uint32;
      }
      list InterfaceSetting {
        key "Interface";
        unique "Alias";
        config true;
        description
        "Note: The {{object}} table includes a unique key
        parameter that is a strong reference.  If a strongly
        referenced object is deleted, the CPE will set the
        referencing parameter to {{empty}}. However, doing so
        under these circumstances might cause the updated
        {{object}} row to then violate the table's unique key
        constraint; if this occurs, the CPE MUST set
        {{param|Status}} to {{enum|Error_Misconfigured|Status}}
        and disable the offending {{object}} row.";
        leaf Enable {
          config true;
          description
          "Enables or disables this {{object}} entry.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Alias {
          config true;
          description
          "{{datatype|expand}}";
          type Alias;
        }
        leaf Interface {
          config true;
          description
          "This is the IP interface associated with this
          {{object}} entry.";
          type string;
        }
        leaf RetransTimer {
          config true;
          description
          "Retransmission interval in {{units}}, as defined in
          {{bibref|RFC4861}}. For auto-configuration purposes,
          {{param}} specifies the delay between consecutive
          Neighbor Solicitation transmissions performed during
          Duplicate Address Detection (DAD)
          {{bibref|RFC4862|Section 5.4}}, as well as the time a
          node waits after sending the last Neighbor
          Solicitation before ending the DAD process.";
          type uint32;
          default "1000";
        }
        leaf RtrSolicitationInterval {
          config true;
          description
          "Retransmission interval in {{units}}, as defined in
          {{bibref|RFC4861}}. For auto-configuration purposes,
          {{param}} specifies the delay between consecutive
          Router Solicitation transmissions.";
          type uint32;
          default "4";
        }
        leaf MaxRtrSolicitations {
          config true;
          description
          "Maximum Number of Router Solicitation Transmission
          messages, as defined in {{bibref|RFC4861}}. For
          auto-configuration purposes {{param}} specifies the
          Maximum Number of Router Solicitation Transmission
          messages to help the host to conclude that there are
          no routers on the link.";
          type uint32;
          default "3";
        }
        leaf NUDEnable {
          config true;
          description
          "Enables or disables Neighbor Unreachability Detection
          (NUD) {{bibref|RFC4861|Section 7}}.";
          type boolean;
        }
        leaf RSEnable {
          config true;
          description
          "Enables or disables Router Solicitation (RS) on
          {{param|Interface}} {{bibref|RFC4861|Section 4.1}}.";
          type boolean;
        }
      }
    }
    container RouterAdvertisement {
      description
      "Information received via router advertisement messages is
      automatically propagated to the relevant
      {{object|.IP.Interface}} sub-objects, e.g.  to the
      {{object|.IP.Interface.{i}.IPv6Address}} and
      {{object|.IP.Interface.{i}.IPv6Prefix}} tables.";
      leaf Enable {
        config true;
        description
        "Enables or disables Router Advertisement.";
        type boolean;
      }
      leaf InterfaceSettingNumberOfEntries {
        config false;
        description
        "{{numentries}}";
        type uint32;
      }
      list InterfaceSetting {
        key "Interface";
        unique "Alias";
        config true;
        description
        "Note: The {{object}} table includes a unique key
        parameter that is a strong reference.  If a strongly
        referenced object is deleted, the CPE will set the
        referencing parameter to {{empty}}. However, doing so
        under these circumstances might cause the updated
        {{object}} row to then violate the table's unique key
        constraint; if this occurs, the CPE MUST set
        {{param|Status}} to {{enum|Error_Misconfigured|Status}}
        and disable the offending {{object}} row.";
        leaf Enable {
          config true;
          description
          "Defines the value of the ''IsRouter'' and
          ''AdvSendAdvertisements'' flags from
          {{bibref|RFC4861|Section 4.2}}";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Alias {
          config true;
          description
          "{{datatype|expand}}";
          type Alias;
        }
        leaf Interface {
          config true;
          description
          "This is the IP interface associated with this
          {{object}} entry.";
          type string;
        }
        leaf-list ManualPrefixes {
          config true;
          description
          "Prefixes MUST be associated with the interface
          instance referenced by {{param|Interface}}.";
          type string;
        }
        leaf-list Prefixes {
          config false;
          description
          "* Prefixes with
          {{param|.IP.Interface.{i}.IPv6Prefix.{i}.Origin}} =
          {{enum|Child|.IP.Interface.{i}.IPv6Prefix.{i}.Origin}}
          or
          {{enum|AutoConfigured|.IP.Interface.{i}.IPv6Prefix.{i}.Origin}}
          associated with the interface instance referenced by
          {{param|Interface}}.";
          type string;
        }
        leaf MaxRtrAdvInterval {
          config true;
          description
          "The maximum time allowed between sending unsolicited
          multicast Router Advertisements from the interface,
          in {{units}} (see {{bibref|RFC4861|Section 4.2}}).";
          type uint32 {
            range "4..1800";
          }
          default "600";
        }
        leaf MinRtrAdvInterval {
          config true;
          description
          "Note: The ''1350'' maximum was derived from the RFC,
          based on 3/4 times the maximum value of
          {{param|MaxRtrAdvInterval}}. Similarly, the ''200''
          default was derived from the RFC, based on 1/3 times
          the default value of {{param|MaxRtrAdvInterval}}.";
          type uint32 {
            range "3..1350";
          }
          default "200";
        }
        leaf AdvDefaultLifetime {
          config true;
          description
          "Note: The ''1800'' default was derived from the RFC,
          based on 3 times the default value of
          {{param|MaxRtrAdvInterval}}.";
          type uint32 {
            range "min..65535";
          }
          default "1800";
        }
        leaf AdvManagedFlag {
          config true;
          description
          "The value placed in the \"Managed address
          configuration\" (M) flag field of Router
          Advertisement messages on this interafce (see
          {{bibref|RFC4861|Section 4.2}}, and
          {{bibref|RFC4862}}).";
          type boolean;
          default "false";
        }
        leaf AdvOtherConfigFlag {
          config true;
          description
          "The value placed in the \"Other configuration\" (O)
          flag field of Router Advertisement messages on this
          interface (see {{bibref|RFC4861|Section 4.2}}, and
          {{bibref|RFC4862}}).";
          type boolean;
          default "false";
        }
        leaf AdvMobileAgentFlag {
          config true;
          description
          "The value placed in the \"Home agent\" (H) flag field
          of Router Advertisement messages on this interface
          (see {{bibref|RFC3775|Section 7.1}}).";
          type boolean;
          default "false";
        }
        leaf AdvPreferredRouterFlag {
          config true;
          description
          "Also see {{bibref|RFC4191|Section 2.1}} which
          discusses how this flag is encoded on the wire.";
          type enumeration {
            enum "High";
            enum "Medium";
            enum "Low";
          }
          default "Medium";
        }
        leaf AdvNDProxyFlag {
          config true;
          description
          "The value placed in the \"Proxy\" (P) flag field of
          Router Advertisement messages on this interface (see
          {{bibref|RFC4389|Section 4.1.3.3}}).";
          type boolean;
          default "false";
        }
        leaf AdvLinkMTU {
          config true;
          description
          "The value placed in MTU options of Router
          Advertisement messages on this interface.  A value of
          zero indicates that no MTU options are included (see
          {{bibref|RFC4861|Section 4.6.4}}).";
          type uint32;
          default "0";
        }
        leaf AdvReachableTime {
          config true;
          description
          "The value zero means unspecified (by the router).";
          type uint32 {
            range "min..3600000";
          }
          default "0";
        }
        leaf AdvRetransTimer {
          config true;
          description
          "The value zero means unspecified (by the router).";
          type uint32;
          default "0";
        }
        leaf AdvCurHopLimit {
          config true;
          description
          "Note: The default can be overridden with the value
          specified in {{bibref|RFC3232}} that was in effect at
          the time of implementation.";
          type uint32 {
            range "min..255";
          }
          default "0";
        }
        leaf OptionNumberOfEntries {
          config false;
          description
          "{{numentries}}";
          type uint32;
        }
        list Option {
          key "Tag";
          unique "Alias";
          config true;
          description
          "This table is intended only for options that are not
          modeled elsewhere.  For example, it is not
          appropriate for the MTU option (which is modeled via
          {{param|#.AdvLinkMTU}}).";
          leaf Enable {
            config true;
            description
            "Enables or disables this {{object}} entry.";
            type boolean;
            default "false";
          }
          leaf Alias {
            config true;
            description
            "{{datatype|expand}}";
            type Alias;
          }
          leaf Tag {
            config true;
            description
            "Option tag (type) {{bibref|RFC4861|Section 4.6}}.";
            type uint32 {
              range "0..65535";
            }
          }
          leaf Value {
            config true;
            description
            "A hexbinary encoded option value
            {{bibref|RFC4861|Section 4.6}}.";
            type yang:hex-string {
              length "0..65535";
            }
          }
        }
      }
    }
    container IPv6rd {
      description
      "See the 6rd Theory of Operation
      {{bibref|TR-181i2a2|Appendix VI}} for a description of
      the working of this 6rd data model.";
      leaf Enable {
        config true;
        description
        "Enables or disables IPv6rd.";
        type boolean;
      }
      leaf InterfaceSettingNumberOfEntries {
        config false;
        description
        "{{numentries}}";
        type uint32;
      }
      list InterfaceSetting {
        key "Alias";
        config true;
        description
        "This object definition is derived from
        {{bibref|RFC5969}} with some minor nomenclature
        changes.";
        leaf Enable {
          config true;
          description
          "Enable or disable this {{object}} instance.";
          type boolean;
        }
        leaf Status {
          config false;
          description
          "The {{enum|Error}} value MAY be used by the CPE to
          indicate a locally defined error condition.";
          type enumeration {
            enum "Disabled";
            enum "Enabled";
            enum "Error";
          }
        }
        leaf Alias {
          config true;
          description
          "{{datatype|expand}}";
          type Alias;
        }
        leaf-list BorderRelayIPv4Addresses {
          config true;
          description
          "List items are the IPv4 addresses (possibly anycast)
          of the 6rd Relay(s).";
          type inet:ipv4-address;
        }
        leaf AllTrafficToBorderRelay {
          config true;
          description
          "If {{true}}, the destination address for all 6rd
          traffic will be set (IPv4 destination address) to one
          of the {{param|BorderRelayIPv4Addresses}}. If
          {{false}}, traffic whose destination address begins
          with the same prefix as {{param|SPIPv6Prefix}} will
          be sent directly to the destination IPv4 address of
          the endpoint, which is in the same 6rd domain.  See
          6rd Theory of Operation for further explanation
          {{bibref|TR-181i2a2|Appendix VI}}.";
          type boolean;
        }
        leaf SPIPv6Prefix {
          config true;
          description
          "The Service Provider's 6rd IPv6 prefix for this
          deployment and this 6rd RG.";
          type inet:ipv6-prefix;
        }
        leaf IPv4MaskLength {
          config true;
          description
          "If the value is 0, then the whole 32 {{units}} of the
          IPv4 address are used in the encoding.";
          type uint32 {
            range "0..32";
          }
        }
        leaf AddressSource {
          config true;
          description
          "{{reference}} Points to the IPv4 address that is the
          source of the IPv4 address embedded in the IPv6 6rd
          prefix, and used as the source encapsulating IPv4
          address.  If the value is {{empty}} or this parameter
          is not present, the device will use internal logic to
          determine which IPv4 source address to use.";
          type string {
            length "0..256";
          }
        }
        leaf TunnelInterface {
          config false;
          description
          "Note: In 6rd, IPv6 packets arriving over one or more
          device LAN IP interfaces are logically fed into this
          {{param}}. Likewise, 6rd traffic from the WAN gets
          logically sent from this {{param}} to LAN IP
          interfaces.";
          type string {
            length "0..256";
          }
        }
        leaf TunneledInterface {
          config false;
          description
          "Note: In 6rd, {{param}} traffic originating from the
          LAN logically feeds into a WAN-side IPv4 capable IP
          interface that the \"IPv6 6rd tunnel\" goes over.
          6rd traffic that enters over this IPv4 WAN interface
          gets logically sent to this {{param}}.";
          type string {
            length "0..256";
          }
        }
      }
    }
    container DSLite {
      description
      "See the Dual-Stack Lite Theory of Operation
      {{bibref|TR-181i2a2|Appendix VII}} for a description of
      the working of this DS-Lite data model.";
      leaf Enable {
        config true;
        description
        "Enables or disables DSLite.";
        type boolean;
      }
      leaf InterfaceSettingNumberOfEntries {
        config false;
        description
        "{{numentries}}";
        type uint32;
      }
      list InterfaceSetting {
        key "Alias";
        config true;
        description
        "DSLite {{bibref|DSLite}} settings.";
        leaf Enable {
          config true;
          description
          "Enable or disable this {{object}} instance.";
          type boolean;
        }
        leaf Status {
          config false;
          description
          "The {{enum|Error}} value MAY be used by the CPE to
          indicate a locally defined error condition.";
          type enumeration {
            enum "Disabled";
            enum "Enabled";
            enum "Error";
          }
        }
        leaf Alias {
          config true;
          description
          "{{datatype|expand}}";
          type Alias;
        }
        leaf EndpointAssignmentPrecedence {
          config true;
          description
          "Indicates the preferred method to be used in
          assigning values to {{param|EndpointName}} when both
          static and dynamic values are available.  See
          {{param|EndpointName}} for further clarification.";
          type enumeration {
            enum "DHCPv6";
            enum "Static";
          }
          default "DHCPv6";
        }
        leaf EndpointAddressTypePrecedence {
          config true;
          description
          "Indicates the preferred method to be used to assign
          the address of the DS-Lite Endpoint when both
          {{param|EndpointName}} and {{param|EndpointAddress}}
          values are available and the
          {{enum|Static|EndpointAssignmentPrecedence}} method
          is used.  See {{param|EndpointName}} and
          {{param|EndpointAddress}} for further clarification.";
          type enumeration {
            enum "FQDN" {
              description
              "Derive from {{param|EndpointName}} via a DNS
              lookup.";
            }
            enum "IPv6Address" {
              description
              "Use {{param|EndpointAddress}} directly.";
            }
          }
        }
        leaf EndpointAddressInUse {
          config false;
          description
          "It is {{empty}} if no endpoint address is currently
          known.";
          type inet:ipv6-address;
        }
        leaf EndpointName {
          config true;
          description
          "Note: {{param}} is only writable when
          {{param|EndpointAssignmentPrecedence}} is
          {{enum|Static|EndpointAssignmentPrecedence}};
          otherwise, {{param}} is automatically configured via
          the DHCPv6 received option.";
          type string {
            length "0..256";
          }
        }
        leaf EndpointAddress {
          config true;
          description
          "This parameter can only be assigned statically (e.g.
          present in the factory default configuration or set
          by the ACS).";
          type inet:ipv6-address;
        }
        leaf Origin {
          config false;
          description
          "Method used to assign {{param|EndpointAddressInUse}}.";
          type enumeration {
            enum "DHCPv6" {
              description
              "Assigned by DHCPv6 {{bibref|RFC3315}}.";
            }
            enum "Static" {
              description
              "For example, present in the factory default
              configuration, set by the ACS, or set by some
              other management entity (e.g.  via a GUI).";
            }
          }
        }
        leaf TunnelInterface {
          config false;
          description
          "Note: In DS-Lite, IPv4 packets arriving over one or
          more device LAN IP interfaces are logically fed into
          this {{param}}. Likewise, DS-Lite traffic from the
          WAN gets logically sent from this {{param}} to LAN IP
          interfaces.";
          type string {
            length "0..256";
          }
        }
        leaf TunneledInterface {
          config false;
          description
          "Note: In DS-Lite, {{param}} traffic originating from
          the LAN logically feeds into a WAN-side IPv6 capable
          IP interface that the \"DSLite IPv4-in-IPv6 tunnel\"
          goes over.  DS-Lite traffic that enters over this
          IPv6 WAN interface gets logically sent to this
          {{param}}.";
          type string {
            length "0..256";
          }
        }
      }
    }
    container QoS {
      description
      "Queue management configuration object.";
      leaf MaxClassificationEntries {
        config false;
        description
        "The maximum number of entries available in the
        Classification table.";
        type uint32;
      }
      leaf ClassificationNumberOfEntries {
        config false;
        description
        "{{numentries}}";
        type uint32;
      }
      leaf MaxAppEntries {
        config false;
        description
        "The maximum number of entries available in the
        {{object|App}} table.";
        type uint32;
      }
      leaf AppNumberOfEntries {
        config false;
        description
        "{{numentries}}";
        type uint32;
      }
      leaf MaxFlowEntries {
        config false;
        description
        "The maximum number of entries available in the
        {{object|Flow}} table.";
        type uint32;
      }
      leaf FlowNumberOfEntries {
        config false;
        description
        "{{numentries}}";
        type uint32;
      }
      leaf MaxPolicerEntries {
        config false;
        description
        "The maximum number of entries available in the
        {{object|Policer}} table.";
        type uint32;
      }
      leaf PolicerNumberOfEntries {
        config false;
        description
        "{{numentries}}";
        type uint32;
      }
      leaf MaxQueueEntries {
        config false;
        description
        "The maximum number of entries available in the
        {{object|Queue}} table.";
        type uint32;
      }
      leaf QueueNumberOfEntries {
        config false;
        description
        "{{numentries}}";
        type uint32;
      }
      leaf QueueStatsNumberOfEntries {
        config false;
        description
        "{{numentries}}";
        type uint32;
      }
      leaf MaxShaperEntries {
        config false;
        description
        "The maximum number of entries available in the
        {{object|Shaper}} table.";
        type uint32;
      }
      leaf ShaperNumberOfEntries {
        config false;
        description
        "{{numentries}}";
        type uint32;
      }
      leaf DefaultForwardingPolicy {
        config true;
        description
        "Identifier of the forwarding policy associated with
        traffic not associated with any specified  classifier.";
        type uint32;
      }
      leaf DefaultTrafficClass {
        config true;
        description
        "Identifier of the traffic class associated with traffic
        not associated with any specified classifier.";
        type uint32;
      }
      leaf DefaultPolicer {
        config true;
        description
        "{{empty}} indicates a null policer.";
        type string {
          length "0..256";
        }
      }
      leaf DefaultQueue {
        config true;
        description
        "{{reference}} Indicates the ''Queue'' table entry for
        traffic not associated with any specified classifier.
        Note: The interpretation of {{empty}} value is
        implementation specific.";
        type string {
          length "0..256";
        }
      }
      leaf DefaultDSCPMark {
        config true;
        description
        "A value of -2 indicates automatic marking of DSCP based
        upon the EthernetPriority value of the incoming packet
        as defined in {{bibref|TR-181i2|Annex A}}.";
        type int32 {
          range "-2..max";
        }
      }
      leaf DefaultEthernetPriorityMark {
        config true;
        description
        "A value of -2 indicates automatic marking of
        EthernetPriority based upon the DSCP value of the
        incoming packet as defined in {{bibref|TR-181i2a5|Annex
        A}}.";
        type int32 {
          range "-2..max";
        }
      }
      leaf DefaultInnerEthernetPriorityMark {
        config true;
        description
        "A value of -2 indicates automatic marking of
        EthernetPriority based upon the DSCP value of the
        incoming packet as defined in {{bibref|TR-181i2|Annex
        A}}.";
        type int32 {
          range "-2..max";
        }
      }
      leaf-list AvailableAppList {
        config false;
        description
        "{{list}} List items represent URNs, each indicating a
        protocol supported for use as a ProtocolIdentifier in
        the App table.  This list MAY include any of the URNs
        defined in {{bibref|TR-181i2|Annex A}} as well as other
        URNs defined elsewhere.";
        type string;
      }
      list Classification {
        key "Alias";
        config true;
        description
        "Several of this object's parameters specify DHCP option
        values.  Some cases are version neutral (the parameter
        can apply to both DHCPv4 and DHCPv6), but in other
        cases the representation of the option is different for
        DHCPv4 and DHCPv6, so it is necessary to define
        separate DHCPv4-specific and DHCPv6-specific
        parameters.  Therefore, an instance of this object that
        uses DHCP option values as classification criteria will
        be associated with either DHCPv4 or DHCPv6, as
        indicated by the {{param|DHCPType}} parameter.";
        leaf Enable {
          config true;
          description
          "Enables or disables this classifier.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Order {
          config true;
          description
          "The value of {{param}} on creation of a {{object}}
          table entry MUST be one greater than the largest
          current value (initially assigned the lowest
          precedence).";
          type uint32 {
            range "1..max";
          }
        }
        leaf Alias {
          config true;
          description
          "{{datatype|expand}}";
          type Alias;
        }
        leaf DHCPType {
          config true;
          description
          "If {{param}} is {{enum|DHCPv4}}, then {{object}}
          parameters that are DHCPv6-specific are ignored.  If
          {{param}} is {{enum|DHCPv6}}, then {{object}}
          parameters that are DHCPv4-specific are ignored.";
          type enumeration {
            enum "DHCPv4";
            enum "DHCPv6";
          }
          default "DHCPv4";
        }
        leaf Interface {
          config true;
          description
          "Note that this parameter is permitted to reference
          ''Tunnel'' instances in order to classify upstream
          packets that have just been encapsulated (such
          packets are conceptually similar to locally-generated
          traffic).  For example, this parameter might
          reference a {{object|.GRE.Tunnel}} or a
          {{object|.MAP.Domain}} instance.";
          type string {
            length "0..256";
          }
        }
        leaf AllInterfaces {
          config true;
          description
          "Classification criterion.  This specifies that all
          ingress interfaces are associated with the entry.  If
          {{true}}, the value of {{param|Interface}} is ignored
          since all ingress interfaces are indicated.";
          type boolean;
          default "false";
        }
        leaf DestIP {
          config true;
          description
          "Destination IP address.  {{empty}} indicates this
          criterion is not used for classification.";
          type inet:ip-address;
        }
        leaf DestMask {
          config true;
          description
          "Destination IP address mask, represented as an IP
          routing prefix using CIDR notation [RFC4632]. The IP
          address part MUST be {{empty}} (and, if specified,
          MUST be ignored).";
          type inet:ip-prefix;
        }
        leaf DestIPExclude {
          config true;
          description
          "If {{true}}, the class includes all packets except
          those that match the (masked) DestIP entry, if
          specified.";
          type boolean;
          default "false";
        }
        leaf SourceIP {
          config true;
          description
          "Source IP address.  {{empty}} indicates this
          criterion is not used for classification.";
          type inet:ip-address;
        }
        leaf SourceMask {
          config true;
          description
          "Source IP address mask, represented as an IP routing
          prefix using CIDR notation [RFC4632]. The IP address
          part MUST be {{empty}} (and, if specified, MUST be
          ignored).";
          type inet:ip-prefix;
        }
        leaf SourceIPExclude {
          config true;
          description
          "If {{true}}, the class includes all packets except
          those that match the (masked) {{param|SourceIP}}
          entry, if specified.";
          type boolean;
          default "false";
        }
        leaf Protocol {
          config true;
          description
          "Protocol number.  A value of -1 indicates this
          criterion is not used for classification.";
          type int32 {
            range "-1..255";
          }
          default "-1";
        }
        leaf ProtocolExclude {
          config true;
          description
          "If {{true}}, the class includes all packets except
          those that match the {{param|Protocol}} entry, if
          specified.";
          type boolean;
          default "false";
        }
        leaf DestPort {
          config true;
          description
          "Destination port number.  A value of -1 indicates
          this criterion is not used for classification.";
          type int32 {
            range "-1..65535";
          }
          default "-1";
        }
        leaf DestPortRangeMax {
          config true;
          description
          "A value of -1 indicates that no port range is
          specified.";
          type int32 {
            range "-1..65535";
          }
          default "-1";
        }
        leaf DestPortExclude {
          config true;
          description
          "If {{true}}, the class includes all packets except
          those that match the {{param|DestPort}} entry (or
          port range), if  specified.";
          type boolean;
          default "false";
        }
        leaf SourcePort {
          config true;
          description
          "Source port number.  A value of -1 indicates this
          criterion is not used for classification.";
          type int32 {
            range "-1..65535";
          }
          default "-1";
        }
        leaf SourcePortRangeMax {
          config true;
          description
          "A value of -1 indicates that no port range is
          specified.";
          type int32 {
            range "-1..65535";
          }
          default "-1";
        }
        leaf SourcePortExclude {
          config true;
          description
          "If {{true}}, the class includes all packets except
          those that match the {{param|SourcePort}} entry (or
          port range), if  specified.";
          type boolean;
          default "false";
        }
        leaf SourceMACAddress {
          config true;
          description
          "Source MAC Address.  {{empty}} indicates this
          criterion is not used for classification.";
          type yang:mac-address;
        }
        leaf SourceMACMask {
          config true;
          description
          "Bit-mask for the MAC address, where matching of a
          packet's MAC address with the
          {{param|SourceMACAddress}} is  only to be done for
          bit positions set to one in the mask.  A mask of
          ''FF:FF:FF:FF:FF:FF'' or {{empty}} indicates all bits
          of the  {{param|SourceMACAddress}} are to be used for
          classification.";
          type yang:mac-address;
        }
        leaf SourceMACExclude {
          config true;
          description
          "If {{true}}, the class includes all packets except
          those that match the (masked)
          {{param|SourceMACAddress}} entry, if  specified.";
          type boolean;
          default "false";
        }
        leaf DestMACAddress {
          config true;
          description
          "The use of destination MAC address as a
          classification criterion is primarily useful only for
          bridged traffic.";
          type yang:mac-address;
        }
        leaf DestMACMask {
          config true;
          description
          "Bit-mask for the MAC address, where matching of a
          packet's MAC address with the
          {{param|DestMACAddress}} is only to be done for bit
          positions set to one in the mask.  A mask of
          ''FF:FF:FF:FF:FF:FF'' or {{empty}} indicates all bits
          of the  {{param|DestMACAddress}} are to be used for
          classification.";
          type yang:mac-address;
        }
        leaf DestMACExclude {
          config true;
          description
          "If {{true}}, the class includes all packets except
          those that match the (masked)
          {{param|DestMACAddress}} entry, if  specified.";
          type boolean;
          default "false";
        }
        leaf Ethertype {
          config true;
          description
          "Ethertype as indicated in either the Ethernet or SNAP
          Type header.  A value of -1 indicates this criterion
          is not used for  classification.";
          type int32 {
            range "-1..max";
          }
          default "-1";
        }
        leaf EthertypeExclude {
          config true;
          description
          "If {{true}}, the class includes all packets except
          those that match the {{param|Ethertype}} entry, if
          specified.";
          type boolean;
          default "false";
        }
        leaf SSAP {
          config true;
          description
          "SSAP element in the LLC header.  A value of -1
          indicates this criterion is not used for
          classification.";
          type int32 {
            range "-1..max";
          }
          default "-1";
        }
        leaf SSAPExclude {
          config true;
          description
          "If {{true}}, the class includes all packets except
          those that match the {{param|SSAP}} entry, if
          specified.";
          type boolean;
          default "false";
        }
        leaf DSAP {
          config true;
          description
          "DSAP element in the LLC header.  A value of -1
          indicates this criterion is not used for
          classification.";
          type int32 {
            range "-1..max";
          }
          default "-1";
        }
        leaf DSAPExclude {
          config true;
          description
          "If {{true}}, the class includes all packets except
          those that match the {{param|DSAP}} entry, if
          specified.";
          type boolean;
          default "false";
        }
        leaf LLCControl {
          config true;
          description
          "Control element in the LLC header.  A value of -1
          indicates this criterion is not used for
          classification.";
          type int32 {
            range "-1..max";
          }
          default "-1";
        }
        leaf LLCControlExclude {
          config true;
          description
          "If {{true}}, the class includes all packets except
          those that match the {{param|LLCControl}} entry, if
          specified.";
          type boolean;
          default "false";
        }
        leaf SNAPOUI {
          config true;
          description
          "OUI element in the SNAP header.  A value of -1
          indicates this criterion is not used for
          classification.";
          type int32 {
            range "-1..max";
          }
          default "-1";
        }
        leaf SNAPOUIExclude {
          config true;
          description
          "If {{true}}, the class includes all packets except
          those that match the {{param|SNAPOUI}} entry, if
          specified.";
          type boolean;
          default "false";
        }
        leaf SourceVendorClassID {
          config true;
          description
          "Note: This parameter is DHCPv4-specific.  It only
          applies when {{param|DHCPType}} is
          {{enum|DHCPv4|DHCPType}}.";
          type string {
            length "0..255";
          }
        }
        leaf SourceVendorClassIDv6 {
          config true;
          description
          "Note: This parameter is DHCPv6-specific.  It only
          applies when {{param|DHCPType}} is
          {{enum|DHCPv6|DHCPType}}.";
          type yang:hex-string {
            length "0..65535";
          }
        }
        leaf SourceVendorClassIDExclude {
          config true;
          description
          "If {{true}}, the class includes all packets except
          those sourced from LAN devices that match the
          {{param|SourceVendorClassID}} entry (for
          {{enum|DHCPv4|DHCPType}}) or the
          {{param|SourceVendorClassIDv6}} entry (for
          {{enum|DHCPv6|DHCPType}}), if specified.";
          type boolean;
          default "false";
        }
        leaf SourceVendorClassIDMode {
          config true;
          description
          "For example, if {{param|SourceVendorClassID}} is
          \"Example\" then an Option 60 value of \"Example
          device\" will match with {{param}}  values of
          {{enum|Prefix}} or {{enum|Substring}}, but not with
          {{enum|Exact}} or {{enum|Suffix}}.";
          type enumeration {
            enum "Exact";
            enum "Prefix";
            enum "Suffix";
            enum "Substring";
          }
          default "Exact";
        }
        leaf DestVendorClassID {
          config true;
          description
          "Note: This parameter is DHCPv4-specific.  It only
          applies when {{param|DHCPType}} is
          {{enum|DHCPv4|DHCPType}}.";
          type string {
            length "0..255";
          }
        }
        leaf DestVendorClassIDv6 {
          config true;
          description
          "Note: This parameter is DHCPv6-specific.  It only
          applies when {{param|DHCPType}} is
          {{enum|DHCPv6|DHCPType}}.";
          type yang:hex-string {
            length "0..65535";
          }
        }
        leaf DestVendorClassIDExclude {
          config true;
          description
          "If {{true}}, the class includes all packets except
          those destined for LAN devices that match the
          {{param|DestVendorClassID}} entry (for
          {{enum|DHCPv4|DHCPType}}) or the
          {{param|DestVendorClassIDv6}} entry (for
          {{enum|DHCPv6|DHCPType}}), if specified.";
          type boolean;
          default "false";
        }
        leaf DestVendorClassIDMode {
          config true;
          description
          "For example, if {{param|DestVendorClassID}} is
          \"Example\" then an Option 60 value of \"Example
          device\" will match with {{param}} values  of
          {{enum|Prefix}} or {{enum|Substring}}, but not with
          {{enum|Exact}} or {{enum|Suffix}}.";
          type enumeration {
            enum "Exact";
            enum "Prefix";
            enum "Suffix";
            enum "Substring";
          }
          default "Exact";
        }
        leaf SourceClientID {
          config true;
          description
          "Note: DHCPv6 Option 1 (Client Identifier) is
          sometimes referred to as ''DUID''.";
          type yang:hex-string {
            length "0..65535";
          }
        }
        leaf SourceClientIDExclude {
          config true;
          description
          "If {{true}}, the class includes all packets except
          those sourced from LAN devices that match the
          {{param|SourceClientID}} entry, if  specified.";
          type boolean;
          default "false";
        }
        leaf DestClientID {
          config true;
          description
          "Note: DHCPv6 Option 1 (Client Identifier) is
          sometimes referred to as ''DUID''.";
          type yang:hex-string {
            length "0..65535";
          }
        }
        leaf DestClientIDExclude {
          config true;
          description
          "If {{true}}, the class includes all packets except
          those destined for LAN devices that match the
          {{param|DestClientID}} entry, if  specified.";
          type boolean;
          default "false";
        }
        leaf SourceUserClassID {
          config true;
          description
          "Note: This parameter is DHCP version neutral.  The
          specific DHCP version in use with this parameter is
          indicated by {{param|DHCPType}}.";
          type yang:hex-string {
            length "0..65535";
          }
        }
        leaf SourceUserClassIDExclude {
          config true;
          description
          "If {{true}}, the class includes all packets except
          those sourced from LAN devices that match the
          {{param|SourceUserClassID}} entry,  if specified.";
          type boolean;
          default "false";
        }
        leaf DestUserClassID {
          config true;
          description
          "Note: This parameter is DHCP version neutral.  The
          specific DHCP version in use with this parameter is
          indicated by {{param|DHCPType}}.";
          type yang:hex-string {
            length "0..65535";
          }
        }
        leaf DestUserClassIDExclude {
          config true;
          description
          "If {{true}}, the class includes all packets except
          those destined for LAN devices that match the
          {{param|DestUserClassID}} entry, if  specified.";
          type boolean;
          default "false";
        }
        leaf SourceVendorSpecificInfo {
          config true;
          description
          "Note: This parameter is DHCP version neutral.  The
          specific DHCP version in use with this parameter is
          indicated by {{param|DHCPType}}.";
          type yang:hex-string {
            length "0..65535";
          }
        }
        leaf SourceVendorSpecificInfoExclude {
          config true;
          description
          "If {{true}}, the class includes all packets except
          those sourced from LAN devices that match the
          {{param|SourceVendorSpecificInfo}}  entry, if
          specified.";
          type boolean;
          default "false";
        }
        leaf SourceVendorSpecificInfoEnterprise {
          config true;
          description
          "The default value (0) is assigned to IANA and will
          probably need to be replaced with an appropriate
          enterprise number.";
          type uint32;
          default "0";
        }
        leaf SourceVendorSpecificInfoSubOption {
          config true;
          description
          "{{param|SourceVendorSpecificInfo}} Sub Option Code as
          defined in {{bibref|RFC3925}}.";
          type int32 {
            range "0..255";
          }
          default "0";
        }
        leaf DestVendorSpecificInfo {
          config true;
          description
          "Note: This parameter is DHCP version neutral.  The
          specific DHCP version in use with this parameter is
          indicated by {{param|DHCPType}}.";
          type yang:hex-string {
            length "0..65535";
          }
        }
        leaf DestVendorSpecificInfoExclude {
          config true;
          description
          "If {{true}}, the class includes all packets except
          those destined for LAN devices that match the
          {{param|DestVendorSpecificInfo}}  entry, if
          specified.";
          type boolean;
          default "false";
        }
        leaf DestVendorSpecificInfoEnterprise {
          config true;
          description
          "The default value (0) is assigned to IANA and will
          probably need to be replaced with an appropriate
          enterprise number.";
          type uint32;
          default "0";
        }
        leaf DestVendorSpecificInfoSubOption {
          config true;
          description
          "{{param|DestVendorSpecificInfo}} Sub Option Code as
          defined in {{bibref|RFC3925}}.";
          type int32 {
            range "0..255";
          }
          default "0";
        }
        leaf TCPACK {
          config true;
          description
          "If {{true}}, this criterion matches with all TCP
          segments that have the ACK control bit set.";
          type boolean;
          default "false";
        }
        leaf TCPACKExclude {
          config true;
          description
          "If {{true}}, the class includes all packets except
          those that match the {{param|TCPACK}} entry, if
          specified.";
          type boolean;
          default "false";
        }
        leaf IPLengthMin {
          config true;
          description
          "Minimum IP Packet Length (including header) in bytes.";
          type uint32;
          default "0";
        }
        leaf IPLengthMax {
          config true;
          description
          "A value of zero indicates that no maximum is
          specified (an umlimited maximum length).";
          type uint32;
          default "0";
        }
        leaf IPLengthExclude {
          config true;
          description
          "If {{true}}, the class includes all packets except
          those whose length (including header) falls within
          the inclusive range  {{param|IPLengthMin}} through
          {{param|IPLengthMax}}.";
          type boolean;
          default "false";
        }
        leaf DSCPCheck {
          config true;
          description
          "A value of -1 indicates this criterion is not used
          for classification.";
          type int32 {
            range "-1..63";
          }
          default "-1";
        }
        leaf DSCPExclude {
          config true;
          description
          "If {{true}}, the class includes all packets except
          those that match the {{param|DSCPCheck}} entry, if
          specified.";
          type boolean;
          default "false";
        }
        leaf DSCPMark {
          config true;
          description
          "A value of -2 indicates automatic marking of DSCP
          based upon the EthernetPriority value of the incoming
          packet as defined in {{bibref|TR-181i2|Annex A}}.";
          type int32 {
            range "-2..max";
          }
          default "-1";
        }
        leaf EthernetPriorityCheck {
          config true;
          description
          "Current Ethernet priority of a VLAN Tag as defined in
          {{bibref|802.1Q-2011}} or Ethernet Priority field as
          defined in 802.1D. If more than 1 VLAN tag is
          present, then this parameter represents the outer
          VLAN Tag.  A value of -1 indicates this criterion is
          not used for classification.";
          type int32 {
            range "-1..max";
          }
          default "-1";
        }
        leaf EthernetPriorityExclude {
          config true;
          description
          "If {{true}}, the class includes all packets except
          those that match the {{param|EthernetPriorityCheck}}
          entry, if  specified.";
          type boolean;
          default "false";
        }
        leaf EthernetPriorityMark {
          config true;
          description
          "A value of -2 indicates automatic marking of
          EthernetPriority based upon the DSCP value of the
          incoming packet as defined in {{bibref|TR-181i2|Annex
          A}}.";
          type int32 {
            range "-2..max";
          }
          default "-1";
        }
        leaf InnerEthernetPriorityCheck {
          config true;
          description
          "Current Ethernet priority of the inner VLAN Tag as
          defined in 802.1Q. This parameter is only applicable
          when the PDU has 2 VLAN Tags.  A value of -1
          indicates this criterion is not used for
          classification.";
          type int32 {
            range "-1..max";
          }
          default "-1";
        }
        leaf InnerEthernetPriorityExclude {
          config true;
          description
          "If {{true}}, the class includes all packets except
          those that match the
          {{param|InnerEthernetPriorityCheck}} entry, if
          specified.";
          type boolean;
          default "false";
        }
        leaf InnerEthernetPriorityMark {
          config true;
          description
          "A value of -2 indicates automatic marking of
          EthernetPriority based upon the DSCP value of the
          incoming packet as defined in {{bibref|TR-181i2|Annex
          A}}.";
          type int32 {
            range "-2..max";
          }
          default "-1";
        }
        leaf EthernetDEICheck {
          config true;
          description
          "Current Ethernet Drop eligible Indication (DEI) of
          the VLAN tag as defined in 802.1Q. If 2 VLAN Tags are
          present, then this parameter represents the outer
          VLAN tag.  A value of -1 indicates this criterion is
          not used for classification.";
          type int32 {
            range "-1..max";
          }
          default "-1";
        }
        leaf EthernetDEIExclude {
          config true;
          description
          "If {{true}}, the class includes all packets except
          those that match the {{param|EthernetDEICheck}}
          entry, if specified.";
          type boolean;
          default "false";
        }
        leaf VLANIDCheck {
          config true;
          description
          "Current Ethernet VLAN ID as defined in 802.1Q.  A
          value of -1 indicates this criterion is not used for
          classification.";
          type int32 {
            range "-1..max";
          }
          default "-1";
        }
        leaf VLANIDExclude {
          config true;
          description
          "If {{true}}, the class includes all packets except
          those that match the {{param|VLANIDCheck}} entry, if
          specified.";
          type boolean;
          default "false";
        }
        leaf OutOfBandInfo {
          config true;
          description
          "If specified, this entry applies to traffic with
          matching out-of-band information.  A value of -1
          indicates this criterion is not  used for
          classification.";
          type int32 {
            range "-1..max";
          }
          default "-1";
        }
        leaf ForwardingPolicy {
          config true;
          description
          "Identifier of the forwarding policy associated with
          traffic that falls in this classification.";
          type uint32;
          default "0";
        }
        leaf TrafficClass {
          config true;
          description
          "{{param}} and {{param|App}} are mutually exclusive
          and one of the two MUST be specified.  If {{param}}
          is {{null}}, {{param|App}} MUST be specified, and
          vice versa.";
          type int32 {
            range "-1..max";
          }
          default "-1";
        }
        leaf Policer {
          config true;
          description
          "{{param}} MAY optionally be specified in conjunction
          with {{param|TrafficClass}}. {{param}} and
          {{param|App}} are mutually exclusive.";
          type string {
            length "0..256";
          }
        }
        leaf App {
          config true;
          description
          "{{param|TrafficClass}} and {{param}} are mutually
          exclusive and one of the two MUST be specified.  If
          {{param|TrafficClass}} is null, {{param}} MUST be
          specified, and vice versa.";
          type string {
            length "0..256";
          }
        }
      }
      list App {
        key "Alias";
        config true;
        description
        "Application table.";
        leaf Enable {
          config true;
          description
          "Enables or disables this App table entry.";
          type boolean;
          default "false";
        }
        leaf Status {
          config false;
          description
          "The {{enum|Error}} value MAY be used by the CPE to
          indicate a locally defined error condition.";
          type enumeration {
            enum "Disabled";
            enum "Enabled";
            enum "Error";
          }
          default "Disabled";
        }
        leaf Alias {
          config true;
          description
          "{{datatype|expand}}";
          type Alias;
        }
        leaf ProtocolIdentifier {
          config true;
          description
          "URN identifying the protocol associated with the
          given application.  A set of defined URNs is given in
          {{bibref|TR-181i2|Annex A}}.";
          type string {
            length "0..256";
          }
        }
        leaf Name {
          config true;
          description
          "Human-readable name associated with this entry in the
          App table.";
          type string {
            length "0..64";
          }
        }
        leaf DefaultForwardingPolicy {
          config true;
          description
          "Identifier of the forwarding policy associated with
          traffic associated with this App table entry, but not
          associated with any specified flow.";
          type uint32;
          default "0";
        }
        leaf DefaultTrafficClass {
          config true;
          description
          "Identifier of the traffic class associated with
          traffic associated with this App table entry, but not
          associated with any specified flow.";
          type uint32;
          default "0";
        }
        leaf DefaultPolicer {
          config true;
          description
          "{{empty}} indicates a null policer.";
          type string {
            length "0..256";
          }
        }
        leaf DefaultDSCPMark {
          config true;
          description
          "A value of -2 indicates automatic marking of DSCP
          based upon the EthernetPriority value of the incoming
          packet as defined in {{bibref|TR-181i2|Annex A}}.";
          type int32 {
            range "-2..max";
          }
          default "-1";
        }
        leaf DefaultEthernetPriorityMark {
          config true;
          description
          "A value of -2 indicates automatic marking of
          EthernetPriority based upon the DSCP value of the
          incoming packet as defined in
          {{bibref|TR-181i2a5|Annex A}}.";
          type int32 {
            range "-2..max";
          }
          default "-1";
        }
        leaf DefaultInnerEthernetPriorityMark {
          config true;
          description
          "A value of -2 indicates automatic marking of
          EthernetPriority based upon the DSCP value of the
          incoming packet as defined in {{bibref|TR-181i2|Annex
          A}}.";
          type int32 {
            range "-2..max";
          }
        }
      }
      list Flow {
        key "Alias";
        config true;
        description
        "Flow table.";
        leaf Enable {
          config true;
          description
          "Enables or disables this Flow table entry.";
          type boolean;
          default "false";
        }
        leaf Status {
          config false;
          description
          "The {{enum|Error}} value MAY be used by the CPE to
          indicate a locally defined error condition.";
          type enumeration {
            enum "Disabled";
            enum "Enabled";
            enum "Error";
          }
          default "Disabled";
        }
        leaf Alias {
          config true;
          description
          "{{datatype|expand}}";
          type Alias;
        }
        leaf Type {
          config true;
          description
          "URN identifying the type of flow to be associated
          with the specified policer.  A set of defined URNs is
          given in {{bibref|TR-181i2|Annex A}}.";
          type string {
            length "0..256";
          }
        }
        leaf TypeParameters {
          config true;
          description
          "List of name-value pairs representing additional
          criteria to identify the flow type.  The use and
          interpretation is specific to the particular FlowType
          URN.Encoded using the \"x-www-form-urlencoded\"
          content type defined in {{bibref|HTML4.01}}.";
          type string {
            length "0..256";
          }
        }
        leaf Name {
          config true;
          description
          "Human-readable name associated with this entry in the
          Flow table.";
          type string {
            length "0..64";
          }
        }
        leaf App {
          config true;
          description
          "{{reference}} Indicates the ''App'' table entry
          associated with this flow.  {{empty}} indicates the
          flow table is not associated with any App table
          entry.";
          type string {
            length "0..256";
          }
        }
        leaf ForwardingPolicy {
          config true;
          description
          "Identifier of the forwarding policy associated with
          this flow.";
          type uint32;
          default "0";
        }
        leaf TrafficClass {
          config true;
          description
          "Identifier of the traffic class associated with this
          flow.";
          type uint32;
          default "0";
        }
        leaf Policer {
          config true;
          description
          "{{empty}} indicates a null policer.";
          type string {
            length "0..256";
          }
        }
        leaf DSCPMark {
          config true;
          description
          "A value of -2 indicates automatic marking of DSCP
          based upon the EthernetPriority value of the incoming
          packet as defined in {{bibref|TR-181i2|Annex A}}.";
          type int32 {
            range "-2..max";
          }
          default "-1";
        }
        leaf EthernetPriorityMark {
          config true;
          description
          "A value of -2 indicates automatic marking of
          EthernetPriority based upon the DSCP value of the
          incoming packet as defined in
          {{bibref|TR-181i2a5|Annex A}}.";
          type int32 {
            range "-2..max";
          }
          default "-1";
        }
        leaf InnerEthernetPriorityMark {
          config true;
          description
          "A value of -2 indicates automatic marking of
          EthernetPriority based upon the DSCP value of the
          incoming packet as defined in {{bibref|TR-181i2|Annex
          A}}.";
          type int32 {
            range "-2..max";
          }
          default "-1";
        }
      }
      list Policer {
        key "Alias";
        config true;
        description
        "Policer table.";
        leaf Enable {
          config true;
          description
          "Enables or disables this policer.";
          type boolean;
          default "false";
        }
        leaf Status {
          config false;
          description
          "The {{enum|Error}} value MAY be used by the CPE to
          indicate a locally defined error condition.";
          type enumeration {
            enum "Disabled";
            enum "Enabled";
            enum "Error";
          }
          default "Disabled";
        }
        leaf Alias {
          config true;
          description
          "{{datatype|expand}}";
          type Alias;
        }
        leaf CommittedRate {
          config true;
          description
          "Committed rate allowed for this policer in {{units}}.";
          type uint32;
          default "0";
        }
        leaf CommittedBurstSize {
          config true;
          description
          "Committed Burstsize in bytes.";
          type uint32;
          default "0";
        }
        leaf ExcessBurstSize {
          config true;
          description
          "Applied for a {{enum|SingleRateThreeColor|MeterType}}
          meter.";
          type uint32;
          default "0";
        }
        leaf PeakRate {
          config true;
          description
          "Applied for {{enum|TwoRateThreeColor|MeterType}}
          meters.";
          type uint32;
          default "0";
        }
        leaf PeakBurstSize {
          config true;
          description
          "Applied for {{enum|TwoRateThreeColor|MeterType}}
          meters.";
          type uint32;
          default "0";
        }
        leaf MeterType {
          config true;
          description
          "{{enum|TwoRateThreeColor}} makes use of
          {{param|CommittedRate}},
          {{param|CommittedBurstSize}}, {{param|PeakRate}}, and
          {{param|PeakBurstSize}} as defined in
          {{bibref|RFC2698}}.";
          type string;
          default "SimpleTokenBucket";
          must ". = ../PossibleMeterTypes";
        }
        leaf-list PossibleMeterTypes {
          config false;
          description
          "{{list}} Indicates supported meter types.";
          type enumeration {
            enum "SimpleTokenBucket";
            enum "SingleRateThreeColor";
            enum "TwoRateThreeColor";
          }
        }
        leaf ConformingAction {
          config true;
          description
          "For example, \"24\" specifies a DSCP value of 24,
          \":3\" specifies an Ethernet Priority of 3, and
          \"24:3\" specifies both.";
          type string {
            pattern "Null|Drop|[0-9]|[1-5][0-9]|6[0-3]|:[0-7]|([0-9]|[1-5][0-9]|6[0-3]):[0-7]";
          }
          default "Null";
        }
        leaf PartialConformingAction {
          config true;
          description
          "For example, \"24\" specifies a DSCP value of 24,
          \":3\" specifies an Ethernet Priority of 3, and
          \"24:3\" specifies both.";
          type string {
            pattern "Null|Drop|[0-9]|[1-5][0-9]|6[0-3]|:[0-7]|([0-9]|[1-5][0-9]|6[0-3]):[0-7]";
          }
          default "Drop";
        }
        leaf NonConformingAction {
          config true;
          description
          "For example, \"24\" specifies a DSCP value of 24,
          \":3\" specifies an Ethernet Priority of 3, and
          \"24:3\" specifies both.";
          type string {
            pattern "Null|Drop|[0-9]|[1-5][0-9]|6[0-3]|:[0-7]|([0-9]|[1-5][0-9]|6[0-3]):[0-7]";
          }
          default "Drop";
        }
        leaf TotalCountedPackets {
          config false;
          description
          "Total number of Packets counted by this policer,
          regardless of meter action.";
          type uint32;
          default "0";
        }
        leaf TotalCountedBytes {
          config false;
          description
          "Total number of Bytes counted by this policer,
          regardless of meter action.";
          type uint32;
          default "0";
        }
        leaf ConformingCountedPackets {
          config false;
          description
          "Number of conforming Packets counted by this policer,
          regardless of meter action.";
          type uint32;
          default "0";
        }
        leaf ConformingCountedBytes {
          config false;
          description
          "Number of conforming Bytes counted by this policer,
          regardless of meter action.";
          type uint32;
          default "0";
        }
        leaf PartiallyConformingCountedPackets {
          config false;
          description
          "Number of partially conforming Packets counted by
          this policer, regardless of meter action.";
          type uint32;
          default "0";
        }
        leaf PartiallyConformingCountedBytes {
          config false;
          description
          "Number of partially conforming Bytes counted by this
          policer, regardless of meter action.";
          type uint32;
          default "0";
        }
        leaf NonConformingCountedPackets {
          config false;
          description
          "Number of non-conforming Packets counted by this
          policer, regardless of meter action.";
          type uint32;
          default "0";
        }
        leaf NonConformingCountedBytes {
          config false;
          description
          "Number of non-conforming Bytes counted by this
          policer, regardless of meter action.";
          type uint32;
          default "0";
        }
      }
      list Queue {
        key "Alias";
        config true;
        description
        "For enabled table entries, if {{param|Interface}} is
        not a valid reference and {{param|AllInterfaces}} is
        {{false}}, then the table entry is inoperable and the
        CPE MUST set {{param|Status}} to
        {{enum|Error_Misconfigured|Status}}.";
        leaf Enable {
          config true;
          description
          "Enables or disables this queue.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Alias {
          config true;
          description
          "{{datatype|expand}}";
          type Alias;
        }
        leaf-list TrafficClasses {
          config true;
          description
          "If more than one queue on a given egress interface is
          associated with a given traffic class, the
          implementation will choose which queue to send
          traffic of this class to.";
          type uint32;
        }
        leaf Interface {
          config true;
          description
          "This MAY be a layer 1, 2 or 3 interface, however, the
          types of interfaces for which ''Queues'' can be
          instantiated is a local matter to the CPE.";
          type string {
            length "0..256";
          }
        }
        leaf AllInterfaces {
          config true;
          description
          "Indicates that the specified queue MUST exist for all
          egress interfaces (i.e.  this queue entry is to apply
          to all egress interfaces). If {{true}}, the value of
          {{param|Interface}} is ignored since all egress
          interfaces are indicated.";
          type boolean;
          default "false";
        }
        leaf HardwareAssisted {
          config false;
          description
          "Indicates whether ''all'' the queues corresponding to
          this table entry are hardware assisted.  If any of
          the queues corresponding to this table entry are not
          hardware assisted, the parameter value MUST be
          {{false}}.";
          type boolean;
          default "false";
        }
        leaf BufferLength {
          config false;
          description
          "Queue buffer size for all egress interfaces for which
          this queue exists.  If the buffer size is not the
          same for all such egress  interfaces, this parameter
          MUST be 0.";
          type uint32;
        }
        leaf Weight {
          config true;
          description
          "Weight of this queue in case of
          {{enum|WFQ|SchedulerAlgorithm}} or
          {{enum|WRR|SchedulerAlgorithm}}, but only  used for
          queues of equal precedence.";
          type uint32;
          default "0";
        }
        leaf Precedence {
          config true;
          description
          "Precedence of this queue relative to others.  Lower
          numbers imply greater precedence.";
          type uint32 {
            range "1..max";
          }
          default "1";
        }
        leaf REDThreshold {
          config true;
          description
          "In this version of the data model, there is no way to
          set the RED weight (''w_q'').  The CPE MUST choose a
          sensible value, e.g.  0.002.";
          type uint32 {
            range "min..100";
          }
          default "0";
        }
        leaf REDPercentage {
          config true;
          description
          "In this version of the data model, there is no way to
          set the RED weight (''w_q'').  The CPE MUST choose a
          sensible value, e.g.  0.002.";
          type uint32 {
            range "min..100";
          }
          default "0";
        }
        leaf DropAlgorithm {
          config true;
          description
          "Dropping algorithm used for this queue if congested.";
          type enumeration {
            enum "RED" {
              description
              "Random Early Detection {{bibref|RED}}";
            }
            enum "DT" {
              description
              "Drop Tail";
            }
            enum "WRED" {
              description
              "Weighted RED";
            }
            enum "BLUE" {
              description
              "{{bibref|BLUE}}";
            }
          }
          default "DT";
        }
        leaf SchedulerAlgorithm {
          config true;
          description
          "Scheduling Algorithm used by scheduler.";
          type enumeration {
            enum "WFQ" {
              description
              "Weighted Fair Queueing";
            }
            enum "WRR" {
              description
              "Weighted Round Robin";
            }
            enum "SP" {
              description
              "Strict Priority";
            }
          }
          default "SP";
        }
        leaf ShapingRate {
          config true;
          description
          "For example, for packets destined for a WAN DSL
          interface, if the egress will be on a PPP or IP link
          with a specified ''ShapingRate'', the percentage is
          calculated relative to this rate.  Otherwise, if the
          ATM layer is rate-constrained, then the rate is
          calculated relative to this rate.  Otherwise, the
          rate is calculated relative to the physical-layer DSL
          rate.";
          type int32 {
            range "-1..max";
          }
          default "-1";
        }
        leaf ShapingBurstSize {
          config true;
          description
          "Burst size in bytes.  For both leaky bucket (constant
          rate shaping) and token bucket (variable rate
          shaping)  this is the bucket size and is therefore
          the maximum burst size.";
          type uint32;
        }
      }
      list QueueStats {
        key "Queue Interface";
        unique "Alias";
        config true;
        description
        "Note: The {{object}} table includes unique key
        parameters that are strong references.  If a strongly
        referenced object is deleted, the CPE will set the
        referencing parameter to {{empty}}. However, doing so
        under these circumstances might cause the updated
        {{object}} row to then violate the table's unique key
        constraint; if this occurs, the CPE MUST disable the
        offending {{object}} row.";
        leaf Enable {
          config true;
          description
          "Enables or disables this object.";
          type boolean;
          default "false";
        }
        leaf Status {
          config false;
          description
          "The status of this object.";
          type enumeration {
            enum "Disabled";
            enum "Enabled" {
              description
              "Enabled and {Queue,Interface} is valid";
            }
            enum "Error" {
              description
              "Enabled but {Queue,Interface} is invalid";
            }
          }
          default "Disabled";
        }
        leaf Alias {
          config true;
          description
          "{{datatype|expand}}";
          type Alias;
        }
        leaf Queue {
          config true;
          description
          "{{reference}} Indicates ''Queue'' entry with which
          this object is associated.";
          type string {
            length "0..256";
          }
        }
        leaf Interface {
          config true;
          description
          "This MAY be a layer 1, 2 or 3 interface, however, the
          types of interfaces for which ''QueueStats'' can be
          instantiated is a local matter to the CPE.";
          type string {
            length "0..256";
          }
        }
        leaf OutputPackets {
          config false;
          description
          "Number of packets output through the queue.";
          type uint32;
          default "0";
        }
        leaf OutputBytes {
          config false;
          description
          "Number of bytes output through the queue.";
          type uint32;
          default "0";
        }
        leaf DroppedPackets {
          config false;
          description
          "Number of packets dropped by the queue.";
          type uint32;
          default "0";
        }
        leaf DroppedBytes {
          config false;
          description
          "Number of bytes dropped by the queue.";
          type uint32;
          default "0";
        }
        leaf QueueOccupancyPackets {
          config false;
          description
          "Queue occupancy in packets (gives a measure of queue
          latency).";
          type uint32;
          default "0";
        }
        leaf QueueOccupancyPercentage {
          config false;
          description
          "Queue occupancy measured as a {{units}}, i.e.  100 *
          queue occupancy in bytes / queue size in bytes (gives
          a measure of queue usage).";
          type uint32 {
            range "0..100";
          }
          default "0";
        }
      }
      list Shaper {
        key "Interface";
        unique "Alias";
        config true;
        description
        "Note: The {{object}} table includes a unique key
        parameter that is a strong reference.  If a strongly
        referenced object is deleted, the CPE will set the
        referencing parameter to {{empty}}. However, doing so
        under these circumstances might cause the updated
        {{object}} row to then violate the table's unique key
        constraint; if this occurs, the CPE MUST set
        {{param|Status}} to {{enum|Error_Misconfigured|Status}}
        and disable the offending {{object}} row.";
        leaf Enable {
          config true;
          description
          "Enables or disables this shaper.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Alias {
          config true;
          description
          "{{datatype|expand}}";
          type Alias;
        }
        leaf Interface {
          config true;
          description
          "{{reference}}The interface object associated with
          this ''Shaper'' entry.  It MAY be a layer 1, 2 or 3
          interface, however, the types of interfaces for which
          ''Shapers'' can be instantiated is a local matter to
          the CPE.";
          type string {
            length "0..256";
          }
        }
        leaf ShapingRate {
          config true;
          description
          "For example, for packets destined for a WAN DSL
          interface, if the ATM layer is rate-constrained, then
          the rate is calculated relative to this rate.
          Otherwise, the rate is calculated relative to the
          physical-layer DSL rate.";
          type int32 {
            range "-1..max";
          }
          default "-1";
        }
        leaf ShapingBurstSize {
          config true;
          description
          "Burst size in bytes.  For both leaky bucket (constant
          rate shaping) and token bucket (variable rate
          shaping)  this is the bucket size and is therefore
          the maximum burst size.";
          type uint32;
        }
      }
    }
    container LANConfigSecurity {
      description
      "This object contains generic device configuration
      information.";
      leaf ConfigPassword {
        config true;
        description
        "If the CPE has a user interface with password
        protection enabled, this parameter is also to be used
        as the user password for  password-protected
        operations.  However, this parameter MUST NOT be used
        to set the user password if the parameter
        {{param|.UserInterface.PasswordUserSelectable}} is
        {{true}}.";
        type string {
          length "0..64";
        }
      }
    }
    container Hosts {
      description
      "This object provides information about each of the hosts
      on the LAN, including those whose IP address was
      allocated by the CPE using DHCP as well as hosts with
      statically allocated IP addresses.  It can also include
      non-IP  hosts.";
      leaf HostNumberOfEntries {
        config false;
        description
        "{{numentries}}";
        type uint32;
      }
      list Host {
        key "PhysAddress";
        unique "Alias";
        config true;
        description
        "Host table.";
        leaf Alias {
          config true;
          description
          "This parameter is DEPRECATED because {{object}} is a
          transient object.";
          type Alias;
        }
        leaf PhysAddress {
          config true;
          description
          "Unique physical identifier of the host.  For many
          layer 2 technologies this is typically a MAC address.";
          type string {
            length "0..64";
          }
        }
        leaf IPAddress {
          config false;
          description
          "If more than one IP address for this host is known,
          the CPE will choose a ''primary'' address.  All known
          IP addresses can be listed in the
          {{object|IPv4Address}} and {{object|IPv6Address}}
          tables.";
          type inet:ip-address;
        }
        leaf AddressSource {
          config false;
          description
          "This parameter is DEPRECATED because only
          {{enum|None}} and {{enum|DHCP}} made sense (the CPE
          doesn't know whether the address is {{enum|Static}}
          or {{enum|AutoIP}}).  The {{enum|DHCP}} case is now
          handled via the {{param|DHCPClient}} reference.";
          type enumeration {
            enum "DHCP";
            enum "Static";
            enum "AutoIP";
            enum "None";
          }
        }
        leaf-list DHCPClient {
          config false;
          description
          "{{reference}} Each list item is the DHCPv4 or DHCPv6
          server's client entry that corresponds to the host.";
          type string;
        }
        leaf LeaseTimeRemaining {
          config false;
          description
          "This parameter is DEPRECATED because DHCP
          lease/lifetime information can be accessed via the
          {{param|DHCPClient}} reference.";
          type int32 {
            range "-1..max";
          }
        }
        leaf AssociatedDevice {
          config false;
          description
          "For example:
          ''Device.WiFi.AccessPoint.1.AssociatedDevice.2''";
          type string {
            length "0..256";
          }
        }
        leaf Layer1Interface {
          config false;
          description
          "For example: ''Device.Ethernet.Interface.2''";
          type string {
            length "0..256";
          }
        }
        leaf Layer3Interface {
          config false;
          description
          "{{reference}}  If the entry represents a non-IP
          device, then {{param}} will be {{empty}}.";
          type string {
            length "0..256";
          }
        }
        leaf VendorClassID {
          config false;
          description
          "This parameter is DEPRECATED because host-supplied
          DHCP options can be accessed via the
          {{param|DHCPClient}} reference.";
          type string {
            length "0..255";
          }
        }
        leaf ClientID {
          config false;
          description
          "This parameter is DEPRECATED because host-supplied
          DHCP options can be accessed via the
          {{param|DHCPClient}} reference.";
          type yang:hex-string {
            length "0..65535";
          }
        }
        leaf UserClassID {
          config false;
          description
          "This parameter is DEPRECATED because host-supplied
          DHCP options can be accessed via the
          {{param|DHCPClient}} reference.";
          type yang:hex-string {
            length "0..65535";
          }
        }
        leaf HostName {
          config false;
          description
          "The device's host name or {{empty}} if unknown.";
          type string {
            length "0..64";
          }
        }
        leaf Active {
          config false;
          description
          "Entries in Device.Hosts.Host SHOULD NOT be removed
          when they become inactive if there are
          {{object|WANStats}} statistics collected for the
          entry in the past seven days.";
          type boolean;
        }
        leaf ActiveLastChange {
          config false;
          description
          "Entries in Device.Hosts.Host SHOULD NOT be removed
          when they become inactive if there are
          {{object|WANStats}} statistics collected for the
          entry in the past seven days.";
          type yang:date-and-time;
        }
        leaf IPv4AddressNumberOfEntries {
          config false;
          description
          "{{numentries}}";
          type uint32;
        }
        leaf IPv6AddressNumberOfEntries {
          config false;
          description
          "{{numentries}}";
          type uint32;
        }
        list IPv4Address {
          key "IPAddress";
          config false;
          description
          "The host's known IPv4 addresses.  This includes any
          addresses assigned via DHCP, which can also be
          accessed via the {{param|#.DHCPClient}} reference.";
          leaf IPAddress {
            config false;
            description
            "IPv4 address.";
            type inet:ipv4-address;
          }
        }
        list IPv6Address {
          key "IPAddress";
          config false;
          description
          "The host's known IPv6 addresses.  This includes any
          addresses assigned via DHCP, which can also be
          accessed via the {{param|#.DHCPClient}} reference.";
          leaf IPAddress {
            config false;
            description
            "IPv6 address.";
            type inet:ipv6-address;
          }
        }
        container WANStats {
          description
          "These count bytes or packets at the IP layer sent to
          the WAN, or received from the WAN.";
          leaf BytesSent {
            config false;
            description
            "The total number of bytes transmitted to the WAN
            from the Host device at the IP layer.";
            type yang:counter32;
          }
          leaf BytesReceived {
            config false;
            description
            "The total number of bytes received from the WAN and
            sent to the Host device at the IP layer.";
            type yang:counter32;
          }
          leaf PacketsSent {
            config false;
            description
            "The total number of IP packets transmitted to the
            WAN from the Host device.";
            type yang:counter32;
          }
          leaf PacketsReceived {
            config false;
            description
            "The total number of IP packets received from the
            WAN and sent to the Host device.";
            type yang:counter32;
          }
          leaf ErrorsSent {
            config false;
            description
            "The total number of outbound IP packets to the WAN
            from the Host device that could not be transmitted
            because of errors.  These may be due to the number
            of retransmissions exceeding the retry limit, or
            from other causes.";
            type yang:counter32;
          }
          leaf RetransCount {
            config false;
            description
            "The total number of transmitted IP packets to the
            WAN from the Host device which were
            retransmissions.  Two retransmissions of the same
            packet results in this counter incrementing by two.";
            type yang:counter32;
          }
          leaf DiscardPacketsSent {
            config false;
            description
            "The total number of outbound IP packets which were
            chosen to be discarded even though no errors had
            been detected to prevent their being transmitted.
            One possible reason for discarding such a packet
            could be to free up buffer space.";
            type yang:counter32;
          }
        }
      }
    }
    container DNS {
      description
      "Properties for Domain Name Service (DNS).";
      leaf-list SupportedRecordTypes {
        config false;
        description
        "The DNS record types that are supported by the device.
        {{enum}}";
        type enumeration {
          enum "A" {
            description
            "{{bibref|RFC1035}}";
          }
          enum "AAAA" {
            description
            "{{bibref|RFC3596}}";
          }
          enum "SRV" {
            description
            "{{bibref|RFC2782}}";
          }
          enum "PTR" {
            description
            "{{bibref|RFC1035}}";
          }
        }
      }
      container Client {
        description
        "Client properties for Domain Name Service (DNS). The
        DNS client resolves FQDN on behalf of device internal
        (client) applications.";
        leaf Enable {
          config true;
          description
          "Enables or disables the DNS client.";
          type boolean;
        }
        leaf Status {
          config false;
          description
          "The {{enum|Error}} value MAY be used by the CPE to
          indicate a locally defined error condition.";
          type enumeration {
            enum "Disabled";
            enum "Enabled";
            enum "Error";
          }
        }
        leaf ServerNumberOfEntries {
          config false;
          description
          "{{numentries}}";
          type uint32;
        }
        list Server {
          key "DNSServer";
          unique "Alias";
          config true;
          description
          "This table contains the DNS Server IP address to be
          used by the DHCP Client (it does ''not'' model a DNS
          Server). Entries are either automatically created as
          result of DHCP (v4 or v6), IPCP, or RA received DNS
          server information, or are statically configured by
          the ACS.";
          leaf Enable {
            config true;
            description
            "Enables or disables this entry.";
            type boolean;
            default "false";
          }
          leaf Status {
            config false;
            description
            "The {{enum|Error}} value MAY be used by the CPE to
            indicate a locally defined error condition.";
            type enumeration {
              enum "Disabled";
              enum "Enabled";
              enum "Error";
            }
            default "Disabled";
          }
          leaf Alias {
            config true;
            description
            "{{datatype|expand}}";
            type Alias;
          }
          leaf DNSServer {
            config true;
            description
            "Note: {{param}} is only writable when
            {{param|Type}} is {{enum|Static|Type}}; otherwise,
            {{param}} is automatically configured as result of
            DHCP, IPCP, or RA received DNS server information.";
            type inet:ip-address;
          }
          leaf Interface {
            config true;
            description
            "Note: {{param}} is only writable when
            {{param|Type}} is {{enum|Static|Type}}; otherwise,
            {{param}} is automatically configured as result of
            DHCP, IPCP, or RA received DNS server information.";
            type string {
              length "0..256";
            }
          }
          leaf Type {
            config false;
            description
            "Table entries that are automatically created as
            result of DHCP, IPCP, or RA received DNS server
            information will have {{param}} set to
            {{enum|DHCPv4}}, {{enum|DHCPv6}}, {{enum|IPCP}}, or
            {{enum|RouterAdvertisement}}, as the case may be.
            Manually created table entires will have their
            {{param}} set to {{enum|Static}}.";
            type enumeration {
              enum "DHCP" {
                description
                "Replaced by {{enum|DHCPv4}}.";
              }
              enum "DHCPv4";
              enum "DHCPv6";
              enum "RouterAdvertisement";
              enum "IPCP";
              enum "Static";
            }
            default "Static";
          }
        }
      }
      container Relay {
        description
        "DNS Relay object.  The DNS proxy (or relay) function
        allows the forwarding of local network DNS queries to
        local or external DNS server(s) {{bibref|RFC5625}}.";
        leaf Enable {
          config true;
          description
          "Enables or disables the DNS Relay function.";
          type boolean;
        }
        leaf Status {
          config false;
          description
          "The {{enum|Error}} value MAY be used by the CPE to
          indicate a locally defined error condition.";
          type enumeration {
            enum "Disabled";
            enum "Enabled";
            enum "Error";
          }
        }
        leaf ForwardNumberOfEntries {
          config false;
          description
          "{{numentries}}";
          type uint32;
        }
        list Forwarding {
          key "DNSServer";
          unique "Alias";
          config true;
          description
          "Note: Management of re-directing queries to the
          device embedded DNS server is not defined in this
          version of the specification.";
          leaf Enable {
            config true;
            description
            "Enables or disables this entry.";
            type boolean;
            default "false";
          }
          leaf Status {
            config false;
            description
            "The {{enum|Error}} value MAY be used by the CPE to
            indicate a locally defined error condition.";
            type enumeration {
              enum "Disabled";
              enum "Enabled";
              enum "Error";
            }
            default "Disabled";
          }
          leaf Alias {
            config true;
            description
            "{{datatype|expand}}";
            type Alias;
          }
          leaf DNSServer {
            config true;
            description
            "Note: {{param}} is only writable when
            {{param|Type}} is {{enum|Static|Type}}; otherwise,
            {{param}} is automatically configured as result of
            DHCP, IPCP, or RA received DNS server information.";
            type inet:ip-address;
          }
          leaf Interface {
            config true;
            description
            "Note: {{param}} is only writable when
            {{param|Type}} is {{enum|Static|Type}}; otherwise,
            {{param}} is automatically configured as result of
            DHCP, IPCP, or RA received DNS server information.";
            type string {
              length "0..256";
            }
          }
          leaf Type {
            config false;
            description
            "Table entries that are automatically created as
            result of DHCP, IPCP, or RA received DNS server
            information will have {{param}} set to
            {{enum|DHCPv4}}, {{enum|DHCPv6}}, {{enum|IPCP}}, or
            {{enum|RouterAdvertisement}}, as the case may be.
            Manually created table entires will have their
            {{param}} set to {{enum|Static}}.";
            type enumeration {
              enum "DHCP" {
                description
                "Replaced by {{enum|DHCPv4}}.";
              }
              enum "DHCPv4";
              enum "DHCPv6";
              enum "RouterAdvertisement";
              enum "IPCP";
              enum "Static";
            }
            default "Static";
          }
        }
      }
      container Diagnostics {
        description
        "The DNS Diagnostics object containing the
        {{object|NSLookupDiagnostics}} test.";
        container NSLookupDiagnostics {
          description
          "Any previous {{object|Result}} instances are removed
          when a new test is initiated.";
          leaf DiagnosticsState {
            config true;
            description
            "While the test is in progress, setting this
            parameter to {{enum|Requested}} (and possibly
            modifying other writable parameters in this object)
            MUST result in the test being terminated and then
            restarted using the current values of the test
            parameters.";
            type enumeration {
              enum "None";
              enum "Requested";
              enum "Complete";
              enum "Error_DNSServerNotResolved" {
                description
                "Unable to resolve DNSServer Name";
              }
              enum "Error_Internal";
              enum "Error_Other";
            }
          }
          leaf Interface {
            config true;
            description
            "If {{empty}} is specified, the CPE MUST use its
            routing policy (Forwarding table entries), if
            necessary, to determine the appropriate interface.";
            type string {
              length "0..256";
            }
          }
          leaf HostName {
            config true;
            description
            "Specifies the Host Name that NS Lookup is to look
            for.  The current domain name MUST be used unless
            the name is a fully qualified name.";
            type string {
              length "0..256";
            }
          }
          leaf DNSServer {
            config true;
            description
            "If {{empty}} is specified, the device's default DNS
            server will be used.";
            type string {
              length "0..256";
            }
          }
          leaf Timeout {
            config true;
            description
            "Timeout in {{units}} that indicates that a request
            has failed.";
            type uint32;
          }
          leaf NumberOfRepetitions {
            config true;
            description
            "Each repetition will use a Result instance to hold
            the NSLookup result data.";
            type uint32;
          }
          leaf SuccessCount {
            config false;
            description
            "Number of successfully executed repetitions.";
            type uint32;
          }
          leaf ResultNumberOfEntries {
            config false;
            description
            "Total number of Result entries from the most recent
            invocation of the test.";
            type uint32;
          }
          list Result {
            key "_id";
            leaf "_id" {
              type "uint32";
            }
            config false;
            description
            "Results from the most recent invocation of the
            test, one instance per repetition.";
            leaf Status {
              config false;
              description
              "A failure on a specific attempt does not mean
              that the overall test failed, but a failure on
              all attempts means that
              {{param|#.DiagnosticsState}} SHOULD be
              {{enum|Error_Other|#.DiagnosticsState}}.";
              type enumeration {
                enum "Success";
                enum "Error_DNSServerNotAvailable";
                enum "Error_HostNameNotResolved";
                enum "Error_Timeout";
                enum "Error_Other";
              }
            }
            leaf AnswerType {
              config false;
              description
              "Result parameter to represent whether the answer
              is Authoritative or not.";
              type enumeration {
                enum "None" {
                  description
                  "Indicates that the NS Lookup failed to find
                  the host.";
                }
                enum "Authoritative";
                enum "NonAuthoritative";
              }
            }
            leaf HostNameReturned {
              config false;
              description
              "Result parameter to represent the fully qualified
              name for the Host Name in the calling parameter
              (e.g.  HostName.DomainName); if no response was
              provided, then this parameter is {{empty}}.";
              type string {
                length "0..256";
              }
            }
            leaf-list IPAddresses {
              config false;
              description
              "{{list}} Indicates the IP Address results
              returned by the NS Lookup; if no response was
              provided, then this parameter is {{empty}}.";
              type inet:ip-address;
            }
            leaf DNSServerIP {
              config false;
              description
              "Result parameter to represent the actual DNS
              Server IP address that the NS Lookup used.";
              type inet:ip-address;
            }
            leaf ResponseTime {
              config false;
              description
              "Response time (for the first response packet) in
              {{units}}, or 0 if no response was received.";
              type uint32;
            }
          }
        }
      }
      container SD {
        description
        "Upon reboot the the contents of the service table are
        repopulated.  When the DNS.SD service is disabled, the
        contents of the service table is implementation
        specific.";
        leaf Enable {
          config true;
          description
          "The parameter, when {{true}}, enables the discovery
          of DNS-SD services hosted by other devices.";
          type boolean;
        }
        leaf ServiceNumberOfEntries {
          config false;
          description
          "{{numentries}}";
          type uint32;
        }
        leaf-list AdvertisedInterfaces {
          config true;
          description
          "If this parameter is not supported by an
          implementation then DNS-SD services are advertised on
          all LAN interfaces.";
          type string;
        }
        list Service {
          key "InstanceName ApplicationProtocol TransportProtocol Domain";
          config false;
          description
          "*{{param|Target}} = \"ssh.example.com.\"";
          leaf InstanceName {
            config false;
            description
            "Human-readable instance name
            {{bibref|DNS-SD|Section 4.1.1 Instance Names}}
            (i.e.  The \"<{{param}}>\" portion of the
            '\"Service Instance Name'\").";
            type string {
              length "0..63";
            }
          }
          leaf ApplicationProtocol {
            config false;
            description
            "The Application Protocol, without the leading
            underscore, associated with the service (e.g.,
            daap) as defined by the DNS-SD service
            {{bibref|DNS-SD|Section 7 Application Protocol
            Names}}.";
            type string {
              length "0..15";
            }
          }
          leaf TransportProtocol {
            config false;
            description
            "The Transport Protocol associated with the service
            as defined by the DNS-SD service
            {{bibref|DNS-SD|Section 4.1.2 Service Names}}.";
            type enumeration {
              enum "TCP";
              enum "UDP";
            }
          }
          leaf Domain {
            config false;
            description
            "The value extracted from the Name field of the DNS
            SRV record {{bibref|RFC2782}} which represents the
            fully qualified domain name (FQDN) associated with
            the service as defined by the DNS-SD service
            {{bibref|DNS-SD|Section 4.1.3 Domain Names}}.";
            type string {
              length "0..256";
            }
          }
          leaf Port {
            config false;
            description
            "The value extracted from the Port field of the DNS
            SRV record {{bibref|RFC2782}} that is used to
            contact the service.";
            type uint32 {
              range "min..65535";
            }
          }
          leaf Target {
            config false;
            description
            "The fully qualified domain name (FQDN) with the
            trailing dot \".\" of the target host implementing
            the service as in the DNS SRV record
            {{bibref|RFC2782}}.";
            type string {
              length "0..256";
            }
          }
          leaf Status {
            config false;
            description
            "The time an inactive {{object}} remains listed in
            this table is a local matter to the device.";
            type enumeration {
              enum "LeaseActive" {
                description
                "The {{object}} has received a response record
                with TTL > 0 and the
                {{param|#.Service.{i}.TimeToLive}} has not
                expired yet.  The {{object}} is considered
                active.";
              }
              enum "GoodbyeReceived" {
                description
                "The device has received a response record
                containing TTL=0 indicating a goodbye message
                and the {{param|#.Service.{i}.TimeToLive}} has
                not expired yet.  The {{object}} is considered
                inactive.";
              }
              enum "LeaseExpired" {
                description
                "The {{param|#.Service.{i}.TimeToLive}} has
                expired.  The {{object}} is considered inactive";
              }
            }
          }
          leaf LastUpdate {
            config false;
            description
            "The date and time at which the last advertisement
            for this {{object}} was received.";
            type yang:date-and-time;
          }
          leaf-list Host {
            config false;
            description
            "{{list}} {{reference|all Host table entries, active
            or inactive, that correspond to this discovered
            DNS.SD service.  As such, when entries are added or
            removed from the Host tables the value of this
            parameter MUST be updated accordingly|ignore}}";
            type string {
              length "0..256";
            }
          }
          leaf TimeToLive {
            config false;
            description
            "The value extracted from the TTL field of the DNS
            SRV record {{bibref|RFC2782}}.";
            type uint32 {
              range "min..2147483647";
            }
          }
          leaf Priority {
            config false;
            description
            "The value extracted from the Priority field of the
            DNS SRV record {{bibref|RFC2782}}.";
            type uint32 {
              range "min..65535";
            }
          }
          leaf Weight {
            config false;
            description
            "A server selection mechanism.  The value extracted
            from the Weight field of the DNS SRV record
            {{bibref|RFC2782}} that specifies the relative
            weight for entries with the same
            {{param|Priority}}.";
            type uint32 {
              range "min..65535";
            }
          }
          leaf TextRecordNumberOfEntries {
            config false;
            description
            "{{numentries}}";
            type uint32;
          }
          list TextRecord {
            key "_id";
            leaf "_id" {
              type "uint32";
            }
            config false;
            description
            "When multiple instances of the {{object}} table
            have the same value for the {{param|Key}}
            parameter, the implementation is CPE specific.";
            leaf Key {
              config false;
              description
              "The key that identifies the text record";
              type string {
                length "0..255";
              }
            }
            leaf Value {
              config false;
              description
              "The value of the text record.";
              type string {
                length "0..255";
              }
            }
          }
        }
      }
    }
    container NAT {
      description
      "The entire {{object}} object only applies to IPv4.";
      leaf InterfaceSettingNumberOfEntries {
        config false;
        description
        "{{numentries}}";
        type uint32;
      }
      leaf PortMappingNumberOfEntries {
        config false;
        description
        "{{numentries}}";
        type uint32;
      }
      list InterfaceSetting {
        key "Interface";
        unique "Alias";
        config true;
        description
        "Note: The {{object}} table includes a unique key
        parameter that is a strong reference.  If a strongly
        referenced object is deleted, the CPE will set the
        referencing parameter to {{empty}}. However, doing so
        under these circumstances might cause the updated
        {{object}} row to then violate the table's unique key
        constraint; if this occurs, the CPE MUST set
        {{param|Status}} to {{enum|Error_Misconfigured|Status}}
        and disable the offending {{object}} row.";
        leaf Enable {
          config true;
          description
          "Enables or disables the {{object}} entry, indicating
          if NAT is enabled for the referenced IP Interface
          instance.   On creation, an {{object}} entry is
          disabled by default.";
          type boolean;
          default "false";
        }
        leaf Status {
          config false;
          description
          "The {{enum|Error}} value MAY be used by the CPE to
          indicate a locally defined error condition.";
          type enumeration {
            enum "Disabled";
            enum "Enabled";
            enum "Enabled_NATForcedDisabled" {
              description
              "NAT enabled but forced by a third party to be
              operationally disabled, e.g.  because a
              {{object|##.MAP.Domain}} is enabled but there is
              no Basic Mapping Rule {{bibref|RFC7597}}.";
            }
            enum "Enabled_PortMappingDisabled" {
              description
              "NAT enabled but port mapping has been
              operationally disabled by a third party, e.g.
              because this is REQUIRED by the current
              {{object|##.Firewall}} level.";
            }
            enum "Error_Misconfigured";
            enum "Error";
          }
          default "Disabled";
        }
        leaf Alias {
          config true;
          description
          "{{datatype|expand}}";
          type Alias;
        }
        leaf Interface {
          config true;
          description
          "{{reference}} The associated IP interface on which
          NAT is to be enabled.";
          type string {
            length "0..256";
          }
        }
      }
      list PortMapping {
        key "RemoteHost ExternalPort Protocol";
        unique "Alias";
        config true;
        description
        "For enabled table entries, if {{param|InternalClient}}
        is {{empty}}, or if {{param|Interface}} is not a valid
        reference and {{param|AllInterfaces}} is {{false}},
        then the table entry is inoperable and the CPE MUST set
        {{param|Status}} to
        {{enum|Error_Misconfigured|Status}}.";
        leaf Enable {
          config true;
          description
          "Enables or disables the port mapping instance.  On
          creation, an entry is disabled by default.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Alias {
          config true;
          description
          "Note: There is no guarantee that the {{param}} value
          on automatically-created {{object}} instances will be
          retained.  This is because automatically-created
          {{object}} instances can be transitory.";
          type Alias;
        }
        leaf Interface {
          config true;
          description
          "{{reference}} Specifies the IP interface to which
          this port mapping applies.";
          type string {
            length "0..256";
          }
        }
        leaf AllInterfaces {
          config true;
          description
          "Indicates whether this port mapping applies to all IP
          interfaces that support port mappings.  If {{true}},
          the value of {{param|Interface}} is ignored since all
          supported IP interfaces are indicated.";
          type boolean;
          default "false";
        }
        leaf LeaseDuration {
          config true;
          description
          "For a dynamic (non-static) port mapping, when this
          parameter is read, the value represents the time
          remaining on the port mapping  lease.  That is, for a
          dynamic port mapping, the value counts down toward 0.
          When a dynamic port mapping lease expires, the CPE
          MUST  automatically terminate that port mapping, and
          MUST automatically delete the corresponding
          {{object}} table entry.";
          type uint32;
        }
        leaf RemoteHost {
          config true;
          description
          "If an incoming packet matches the criteria associated
          with more than one entry in this table, the CPE MUST
          apply the port mapping associated with the highest
          precedence entry.";
          type string;
        }
        leaf ExternalPort {
          config true;
          description
          "If an incoming packet matches the criteria associated
          with more than one entry in this table, the CPE MUST
          apply the port mapping associated with the highest
          precedence entry.";
          type uint32 {
            range "0..65535";
          }
        }
        leaf ExternalPortEndRange {
          config true;
          description
          "If specified, the value of this parameter MUST be
          greater than or equal to the value of
          {{param|ExternalPort}}.";
          type uint32 {
            range "0..65535";
          }
          default "0";
        }
        leaf InternalPort {
          config true;
          description
          "The port on {{param|InternalClient}} that the gateway
          SHOULD forward traffic to.";
          type uint32 {
            range "0..65535";
          }
        }
        leaf Protocol {
          config true;
          description
          "The protocol of the port mapping.  {{enum}}";
          type enumeration {
            enum "TCP";
            enum "UDP";
          }
        }
        leaf InternalClient {
          config true;
          description
          "It MUST be possible to set the {{param}} to the
          broadcast IP address 255.255.255.255 for UDP
          mappings.  This is to enable multiple NAT clients to
          use the same well-known port simultaneously.";
          type string {
            length "0..256";
          }
        }
        leaf Description {
          config true;
          description
          "User-readable description of this port mapping.";
          type string {
            length "0..256";
          }
        }
      }
    }
    container PCP {
      description
      "See the PCP Theory of Operation
      {{bibref|TR-181i2a8|Appendix XIV}} for a description of
      the working of this PCP data model.";
      leaf-list SupportedVersions {
        config false;
        description
        "This parameter is based on Version from
        {{bibref|RFC6887}}.";
        type uint32 {
          range "0..65535";
        }
      }
      leaf PreferredVersion {
        config true;
        description
        "The factory default MUST be the highest supported
        version, as described in {{bibref|RFC6887|Section 9}}.";
        type uint32 {
          range "0..65535";
        }
      }
      leaf-list OptionList {
        config false;
        description
        "{{list}} The list of the PCP Options supported by the
        PCP Client.";
        type uint32 {
          range "0..254";
        }
      }
      leaf ClientNumberOfEntries {
        config false;
        description
        "{{numentries}}";
        type uint32;
      }
      list Client {
        key "WANInterface";
        unique "Alias";
        config true;
        description
        "Client properties for Port Control Protocol (PCP). The
        PCP Client interacts with a PCP Server as defined in
        {{bibref|RFC6887}} for internal device applications or
        LAN device applications via Interworking functions.";
        leaf Enable {
          config true;
          description
          "Enables or disables the PCP Client.";
          type boolean;
        }
        leaf Alias {
          config true;
          description
          "{{datatype|expand}}";
          type Alias;
        }
        leaf WANInterface {
          config true;
          description
          "{{reference|the interface stack instance representing
          the WAN interface this client operates on}} See
          {{object|.InterfaceStack.}}";
          type string;
        }
        leaf Status {
          config false;
          description
          "The {{enum|Error}} value MAY be used by the CPE to
          indicate a locally defined error condition.";
          type enumeration {
            enum "Disabled";
            enum "Enabled";
            enum "Error";
          }
        }
        leaf MAPEnable {
          config true;
          description
          "Enables or disables the MAP OpCode.";
          type boolean;
        }
        leaf PEEREnable {
          config true;
          description
          "Enables or disables the PEER OpCode.";
          type boolean;
        }
        leaf ANNOUNCEEnable {
          config true;
          description
          "When {{false}} the PCP Client does not support
          unsolicited ANNOUNCE messages.";
          type boolean;
        }
        leaf THIRDPARTYEnable {
          config true;
          description
          "Enables or disables the THIRD_PARTY Option.";
          type boolean;
        }
        leaf THIRDPARTYStatus {
          config false;
          description
          "The {{enum|Error}} value MAY be used by the CPE to
          indicate a locally defined error condition.";
          type enumeration {
            enum "Disabled";
            enum "Enabled";
            enum "Error";
          }
        }
        leaf FILTEREnable {
          config true;
          description
          "Enables or disables the FILTER option.";
          type boolean;
        }
        leaf ServerNumberOfEntries {
          config false;
          description
          "{{numentries}}";
          type uint32;
        }
        container PCPProxy {
          description
          "Properties for the Port Control Protocol (PCP) Proxy,
          as specified in {{bibref|PCPProxy}}.";
          leaf Enable {
            config true;
            description
            "Enables or disables the PCP Proxy for this PCP
            Client.";
            type boolean;
          }
          leaf HighestVersion {
            config false;
            description
            "This parameter is based on Version from
            {{bibref|RFC6887}}.";
            type uint32 {
              range "0..65535";
            }
          }
          leaf Status {
            config false;
            description
            "The {{enum|Error}} value MAY be used by the CPE to
            indicate a locally defined error condition.";
            type enumeration {
              enum "Disabled";
              enum "Enabled";
              enum "Error";
            }
          }
        }
        container UPnPIWF {
          description
          "Properties for the interworking function between UPnP
          IGD (Internet Gateway Device) and PCP, as specified
          in {{bibref|RFC6970}}.";
          leaf Enable {
            config true;
            description
            "Enables or disables the UPnP IGD-PCP Interworking
            Function for this PCP Client.";
            type boolean;
          }
          leaf Status {
            config false;
            description
            "The {{enum|Error}} value MAY be used by the CPE to
            indicate a locally defined error condition.";
            type enumeration {
              enum "Disabled";
              enum "Enabled";
              enum "Error";
            }
          }
        }
        list Server {
          key "ServerNameOrAddress";
          unique "Alias";
          config true;
          description
          "Each OPTION_V4_PCP_SERVER or OPTION_V6_PCP_SERVER
          option corresponds to a {{object}} instance.  If an
          option returns multiple addresses then that
          {{object}} instance has multiple addresses.";
          leaf Enable {
            config true;
            description
            "Enables or disables this PCP Server.";
            type boolean;
            default "true";
          }
          leaf Status {
            config false;
            description
            "The {{enum|Error}} value MAY be used by the CPE to
            indicate a locally defined error condition.";
            type enumeration {
              enum "Disabled";
              enum "Enabled";
              enum "Connecting";
              enum "Error_Timeout";
              enum "Error_HostNameNotResolved";
              enum "Error_NetworkFailure";
              enum "Error_NotAuthorized";
              enum "Error_Unsupported";
              enum "Error";
            }
            default "Disabled";
          }
          leaf Alias {
            config true;
            description
            "{{datatype|expand}}";
            type Alias;
          }
          leaf Origin {
            config false;
            description
            "Note: In the {{enum|DHCPv4}} and {{enum|DHCPv6}}
            cases, if more than one IP address is received
            {{param|ServerNameOrAddress}} will be the first
            address and {{param|AdditionalServerAddresses}}
            will be the remaining addresses.";
            type enumeration {
              enum "DHCPv4" {
                description
                "{{param|ServerNameOrAddress}} is an IPv4
                address that was received via
                OPTION_V4_PCP_SERVER";
              }
              enum "DHCPv6" {
                description
                "{{param|ServerNameOrAddress}} is an IPv6
                address that was received via
                OPTION_V6_PCP_SERVER";
              }
              enum "Static" {
                description
                "{{param|ServerNameOrAddress}} is an FQDN, IPv4
                address or IPv6 address that was created by the
                ACS, by some other management entity (e.g.  via
                a GUI), or is present in the factory default
                configuration";
              }
            }
            default "Static";
          }
          leaf ServerNameOrAddress {
            config true;
            description
            "The FQDN or IP address of the PCP Server, assigned
            as described under {{param|Origin}}.";
            type string {
              length "0..256";
            }
          }
          leaf ServerAddressInUse {
            config false;
            description
            "{{empty}} indicates that no PCP Server address is
            currently known.";
            type inet:ip-address;
          }
          leaf-list AdditionalServerAddresses {
            config false;
            description
            "PCP Server addresses in addition to
            {{param|ServerNameOrAddress}}.  This can be
            non-empty only if {{param|Origin}} is
            {{enum|DHCPv4|Origin}} or {{enum|DHCPv6|Origin}}
            and if more than one PCP Server address was
            received.";
            type inet:ip-address;
          }
          leaf ExternalIPAddress {
            config false;
            description
            "The external IP address of the PCP-controlled
            device hosting this server.";
            type inet:ip-address;
          }
          leaf CurrentVersion {
            config false;
            description
            "This parameter is based on Version from
            {{bibref|RFC6887}}.";
            type uint32 {
              range "0..65535";
            }
          }
          leaf MaximumFilters {
            config true;
            description
            "Indicates the maximum number of inbound filters
            allowed to be associated with a mapping entry on
            this server.";
            type uint32;
          }
          leaf PortQuota {
            config true;
            description
            "A value of 0 means that there is no limitation.";
            type uint32 {
              range "min..65535";
            }
            default "0";
          }
          leaf PreferredLifetime {
            config true;
            description
            "Indicates the preferred lifetime (in {{units}}) to
            be used for mappings with this server when no
            preference is selected by an application/user.";
            type uint32;
          }
          leaf-list Capabilities {
            config false;
            description
            "Indicates the capabilities supported by the PCP
            Server.  {{enum}}";
            type enumeration {
              enum "NAT44";
              enum "StatelessNAT64";
              enum "StatefulNAT64";
              enum "A+PPortRangeRouter";
              enum "SupportsPORTSETOption";
              enum "IPv4Firewall";
              enum "IPv6Firewall";
              enum "NPTv6";
              enum "DSCPReMarkingFunction";
              enum "FLOWDATAAwareFunction";
              enum "ILNPTranslator";
            }
          }
          leaf InboundMappingNumberOfEntries {
            config false;
            description
            "{{numentries}}";
            type uint32;
          }
          leaf OutboundMappingNumberOfEntries {
            config false;
            description
            "{{numentries}}";
            type uint32;
          }
          list InboundMapping {
            key "InternalPort ProtocolNumber ThirdPartyAddress";
            unique "Alias";
            config true;
            description
            "For non-{{enum|Static|Origin}} mappings (here
            ''Static'' refers to the mechanism that created the
            mapping, not to the {{param|Lifetime}}), the ACS
            MAY modify the {{param||Enable}} parameter but MUST
            NOT modify any other parameters in the mapping or
            its sub-objects.";
            leaf Enable {
              config true;
              description
              "Enables or disables this {{object}} instance.";
              type boolean;
              default "false";
            }
            leaf Status {
              config false;
              description
              "The {{enum|Error}} value MAY be used by the CPE
              to indicate a locally defined error condition.";
              type enumeration {
                enum "Disabled";
                enum "Enabled";
                enum "Error_PCPErrorCodeReceived";
                enum "Error";
              }
              default "Disabled";
            }
            leaf ErrorCode {
              config false;
              description
              "Provides the PCP error code when {{param|Status}}
              is {{enum|Error_PCPErrorCodeReceived|Status}}.
              Error code values are defined in
              {{bibref|RFC6887|Section 7.4}}.";
              type uint32 {
                range "1..255";
              }
            }
            leaf Alias {
              config true;
              description
              "{{datatype|expand}}";
              type Alias;
            }
            leaf Origin {
              config false;
              description
              "Mechanism via which the mapping was requested.
              {{enum}}";
              type enumeration {
                enum "Internal" {
                  description
                  "Requested via internal device application";
                }
                enum "UPnP_IWF" {
                  description
                  "Requested via UPnP IGD interworking function";
                }
                enum "PCP_Proxy" {
                  description
                  "Requested via PCP proxy";
                }
                enum "Static" {
                  description
                  "Requested via static configuration, i.e.
                  created by the ACS, by some other management
                  entity (e.g.  via a GUI), or is present in
                  the factory default configuration";
                }
              }
            }
            leaf Lifetime {
              config true;
              description
              "When a dynamic Inbound Mapping lease expires, the
              CPE MUST automatically delete the corresponding
              {{object}} table entry.";
              type uint32;
            }
            leaf SuggestedExternalIPAddress {
              config true;
              description
              "This is useful for refreshing an Inbound Mapping,
              especially after the PCP Server loses state.  If
              the PCP client does not know the external
              address, or does not have a preference, it MUST
              use {{empty}}.";
              type inet:ip-address;
            }
            leaf SuggestedExternalPort {
              config true;
              description
              "This is useful for refreshing an Inbound Mapping,
              especially after the PCP Server loses state.  If
              the PCP Client does not know the external port,
              or does not have a preference, it MUST use 0.";
              type uint32 {
                range "0..65535";
              }
              default "0";
            }
            leaf SuggestedExternalPortEndRange {
              config true;
              description
              "If specified, the value of this parameter MUST be
              zero or be greater than or equal to the value of
              {{param|SuggestedExternalPort}}.";
              type uint32 {
                range "0..65535";
              }
              default "0";
            }
            leaf InternalPort {
              config true;
              description
              "The port on this PCP Client's
              {{param|##.WANInterface}} that the PCP-controlled
              device forwards incoming packets to.";
              type uint32 {
                range "1..65535";
              }
            }
            leaf ProtocolNumber {
              config true;
              description
              "The value -1 means ''all protocols''.";
              type int32 {
                range "-1..255";
              }
            }
            leaf ThirdPartyAddress {
              config true;
              description
              "For non-third-party mappings, {{param}} SHOULD be
              {{empty}}.";
              type inet:ip-address;
            }
            leaf Description {
              config true;
              description
              "User-readable description of this {{object}}.";
              type string {
                length "0..256";
              }
            }
            leaf AssignedExternalIPAddress {
              config false;
              description
              "The external IPAddress returned by the PCP
              Server.  The IP address that the PCP-controlled
              device is listening on for incoming packets to a
              corresponding PCP Client.";
              type inet:ip-address;
            }
            leaf AssignedExternalPort {
              config false;
              description
              "The external port returned by the PCP Server.
              The external port (or the first port of a range
              of external ports) that the PCP-controlled device
              is listening on for incoming packets to a
              corresponding {{param|InternalPort}}. Inbound
              packets to this external port on the External
              interface of the PCP-controlled device is
              forwarded to the on the {{param|InternalPort}}.";
              type uint32 {
                range "0..65535";
              }
            }
            leaf AssignedExternalPortEndRange {
              config false;
              description
              "A value of zero (0) indicates that no external
              port range is specified, i.e.  that the range
              consists only of {{param|AssignedExternalPort}}.";
              type uint32 {
                range "0..65535";
              }
              default "0";
            }
            leaf FilterNumberOfEntries {
              config false;
              description
              "{{numentries}}";
              type uint32;
            }
            list Filter {
              key "Alias";
              config true;
              description
              "This table contains all Filters restricting this
              Inbound Mapping, as defined in
              {{bibref|RFC6887|}}.";
              leaf Alias {
                config true;
                description
                "{{datatype|expand}}";
                type Alias;
              }
              leaf RemoteHostIPAddress {
                config true;
                description
                "Permitted remote peer IP address for this
                filter.";
                type inet:ip-address;
              }
              leaf PrefixLength {
                config true;
                description
                "Indicates how many bits of
                {{param|RemoteHostIPAddress}} are relevant for
                this filter.";
                type uint32 {
                  range "1..128";
                }
                default "128";
              }
              leaf RemotePort {
                config true;
                description
                "The value 0 indicates ''all ports''.";
                type uint32 {
                  range "0..65535";
                }
              }
              leaf RemotePortEndRange {
                config false;
                description
                "A value of zero (0) indicates that no remote
                port range is specified, i.e.  that the range
                consists only of {{param|RemotePort}}.";
                type uint32 {
                  range "0..65535";
                }
                default "0";
              }
            }
          }
          list OutboundMapping {
            key "InternalPort ProtocolNumber ThirdPartyAddress RemoteHostIPAddress RemotePort";
            unique "Alias";
            config true;
            description
            "For non-{{enum|Static|Origin}} mappings (here
            ''Static'' refers to the mechanism that created the
            mapping, not to the {{param|Lifetime}}), the ACS
            MAY modify the {{param||Enable}} parameter but MUST
            NOT modify any other parameters in the mapping or
            its sub-objects.";
            leaf Enable {
              config true;
              description
              "Enables or disables this {{object}} instance.";
              type boolean;
              default "false";
            }
            leaf Status {
              config false;
              description
              "The {{enum|Error}} value MAY be used by the CPE
              to indicate a locally defined error condition.";
              type enumeration {
                enum "Disabled";
                enum "Enabled";
                enum "Error_PCPErrorCodeReceived";
                enum "Error";
              }
              default "Disabled";
            }
            leaf ErrorCode {
              config false;
              description
              "Provides the PCP Error code when {{param|Status}}
              is {{enum|Error_PCPErrorCodeReceived|Status}}.
              Error code values are defined in
              {{bibref|RFC6887|Section 7.4}}.";
              type uint32 {
                range "1..255";
              }
            }
            leaf Alias {
              config true;
              description
              "{{datatype|expand}}";
              type Alias;
            }
            leaf Origin {
              config false;
              description
              "Mechanism via which the mapping was requested.
              {{enum}}";
              type enumeration {
                enum "Internal" {
                  description
                  "Requested via internal device application";
                }
                enum "UPnP_IWF" {
                  description
                  "Requested via UPnP IGD interworking function";
                }
                enum "PCP_Proxy" {
                  description
                  "Requested via PCP proxy";
                }
                enum "Static" {
                  description
                  "Requested via static configuration, i.e.
                  created by the ACS, by some other management
                  entity (e.g.  via a GUI), or is present in
                  the factory default configuration";
                }
              }
            }
            leaf Lifetime {
              config true;
              description
              "When a dynamic Outbound Mapping lease expires,
              the CPE MUST automatically delete the
              corresponding {{object}} table entry.";
              type uint32;
            }
            leaf SuggestedExternalIPAddress {
              config true;
              description
              "This is useful for refreshing a mapping,
              especially after the PCP Server has lost state.
              If the PCP Client does not know the external
              address, or does not have a preference, it MUST
              use {{empty}}.";
              type inet:ip-address;
            }
            leaf SuggestedExternalPort {
              config true;
              description
              "This is useful for refreshing a mapping,
              especially after the PCP Server has lost state.
              If the PCP Client does not know the external
              port, or does not have a preference, it MUST use
              0.";
              type uint32 {
                range "0..65535";
              }
              default "0";
            }
            leaf RemoteHostIPAddress {
              config true;
              description
              "The remote peer's IP address, as seen from the
              PCP Client, for this Outbound Mapping.";
              type inet:ip-address;
            }
            leaf InternalPort {
              config true;
              description
              "The port on PCP Client WAN Interface that the
              PCP-controlled device SHOULD listen to for this
              mapping.";
              type uint32 {
                range "1..65535";
              }
            }
            leaf RemotePort {
              config true;
              description
              "The remote peer's port, as seen from the PCP
              Client, for this Outbound Mapping.";
              type uint32 {
                range "1..65535";
              }
            }
            leaf ProtocolNumber {
              config true;
              description
              "The value -1 means ''all protocols''.";
              type int32 {
                range "-1..255";
              }
            }
            leaf ThirdPartyAddress {
              config true;
              description
              "For non-third-party mappings, {{param}} SHOULD be
              {{empty}}.";
              type inet:ip-address;
            }
            leaf Description {
              config true;
              description
              "User-readable description of this {{object}}.";
              type string {
                length "0..256";
              }
            }
            leaf AssignedExternalIPAddress {
              config false;
              description
              "The external IP address returned by the PCP
              Server.  The IP address that the PCP-controlled
              device uses to send outgoing packets
              corresponding to this mapping.";
              type inet:ip-address;
            }
            leaf AssignedExternalPort {
              config false;
              description
              "The external port returned by the PCP Server.
              The port that the PCP-controlled device uses to
              send outgoing packets corresponding to this
              mapping.";
              type uint32 {
                range "0..65535";
              }
            }
          }
        }
      }
    }
    container DHCPv4 {
      description
      "The Dynamic Host Configuration Protocol (DHCP) IPv4
      object {{bibref|RFC2131}}. This entire object applies to
      IPv4 only.  It contains the {{object|Client}},
      {{object|Server}}, and {{object|Relay}} objects.";
      leaf ClientNumberOfEntries {
        config false;
        description
        "{{numentries}}";
        type uint32;
      }
      list Client {
        key "Interface";
        unique "Alias";
        config true;
        description
        "Note: The {{object}} table includes a unique key
        parameter that is a strong reference.  If a strongly
        referenced object is deleted, the CPE will set the
        referencing parameter to {{empty}}. However, doing so
        under these circumstances might cause the updated
        {{object}} row to then violate the table's unique key
        constraint; if this occurs, the CPE MUST set
        {{param|Status}} to {{enum|Error_Misconfigured|Status}}
        and disable the offending {{object}} row.";
        leaf Enable {
          config true;
          description
          "Enables or disables the DHCP Client entry.";
          type boolean;
          default "false";
        }
        leaf Alias {
          config true;
          description
          "{{datatype|expand}}";
          type Alias;
        }
        leaf Interface {
          config true;
          description
          "{{reference}} The IP Interface associated with the
          ''Client'' entry.";
          type string {
            length "0..256";
          }
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf DHCPStatus {
          config false;
          description
          "Note: This value is only relevant when the DHCP
          Client is operationally enabled (i.e.  when
          {{param|Status}} is {{enum|Enabled|Status}}).";
          type enumeration {
            enum "Init";
            enum "Selecting";
            enum "Requesting";
            enum "Rebinding";
            enum "Bound";
            enum "Renewing";
          }
        }
        leaf Renew {
          config true;
          description
          "When set to {{true}}, the DHCP client will renew its
          DHCP lease.";
          type boolean;
          default "false";
        }
        leaf IPAddress {
          config false;
          description
          "IPv4 Address option received from the DHCP Server.
          {{empty}} when {{param|Status}} is not equal to
          {{enum|Bound|DHCPStatus}}.";
          type inet:ipv4-address;
        }
        leaf SubnetMask {
          config false;
          description
          "Value is information received via DHCP Option 1.";
          type inet:ipv4-address;
        }
        leaf-list IPRouters {
          config false;
          description
          "Value is information received via DHCP Options 3, 33
          or 121.";
          type inet:ipv4-address;
        }
        leaf-list DNSServers {
          config false;
          description
          "Value is information received via DHCP Option 6.";
          type inet:ipv4-address;
        }
        leaf LeaseTimeRemaining {
          config false;
          description
          "DHCP lease time remaining in {{units}}. A value of -1
          indicates an infinite lease.";
          type int32 {
            range "-1..max";
          }
          default "0";
        }
        leaf DHCPServer {
          config false;
          description
          "The IPv4 address of the current DHCP server.";
          type inet:ipv4-address;
        }
        leaf PassthroughEnable {
          config true;
          description
          "If {{true}}, the DHCP Client retrieved information is
          propagated to the parameters in the referenced
          {{param|PassthroughDHCPPool}} object, replacing any
          existing configuration (including ''MinAddress'',
          ''MaxAddress'', ''SubnetMask'', ''IPRouters'', and
          ''DNSServers'').";
          type boolean;
          default "false";
        }
        leaf PassthroughDHCPPool {
          config true;
          description
          "{{reference}}When {{param}} is set to {{empty}},
          {{param|PassthroughEnable}} MUST be set to {{false}}
          (i.e.  passthrough can not be enabled without a pool
          reference specified).";
          type string {
            length "0..256";
          }
        }
        leaf SentOptionNumberOfEntries {
          config false;
          description
          "{{numentries}}";
          type uint32;
        }
        leaf ReqOptionNumberOfEntries {
          config false;
          description
          "{{numentries}}";
          type uint32;
        }
        list SentOption {
          key "Tag";
          unique "Alias";
          config true;
          description
          "Each instance of this object represents a DHCP option
          that MUST, if enabled, be sent in DHCP client
          requests.  All  sent DHCP options MUST be listed.";
          leaf Enable {
            config true;
            description
            "Enables or disables this SentOption table entry.";
            type boolean;
            default "false";
          }
          leaf Alias {
            config true;
            description
            "{{datatype|expand}}";
            type Alias;
          }
          leaf Tag {
            config true;
            description
            "Option tag as defined in {{bibref|RFC2132}}.";
            type uint32 {
              range "1..254";
            }
          }
          leaf Value {
            config true;
            description
            "A hexbinary encoded option value.";
            type yang:hex-string {
              length "0..255";
            }
          }
        }
        list ReqOption {
          key "Tag";
          unique "Alias";
          config true;
          description
          "Each instance of this object represents a DHCP option
          that MUST, if enabled, be requested in DHCP client
          requests.  All requested DHCP options MUST be listed.";
          leaf Enable {
            config true;
            description
            "Enables or disables this ReqOption table entry.";
            type boolean;
            default "false";
          }
          leaf Order {
            config true;
            description
            "The value of {{param}} on creation of a {{object}}
            table entry MUST be one greater than the largest
            current value.";
            type uint32 {
              range "1..max";
            }
          }
          leaf Alias {
            config true;
            description
            "{{datatype|expand}}";
            type Alias;
          }
          leaf Tag {
            config true;
            description
            "Option tag as defined in {{bibref|RFC2132}}.";
            type uint32 {
              range "1..254";
            }
          }
          leaf Value {
            config false;
            description
            "Received DHCP option values MAY, but need not,
            persist across CPE reboots.";
            type yang:hex-string {
              length "0..255";
            }
          }
        }
      }
      container Server {
        description
        "DHCP server configuration.";
        leaf Enable {
          config true;
          description
          "Enables or disables the DHCP server.";
          type boolean;
        }
        leaf PoolNumberOfEntries {
          config false;
          description
          "{{numentries}}";
          type uint32;
        }
        list Pool {
          key "Alias";
          config true;
          description
          "For enabled table entries, if {{param|Interface}} is
          not a valid reference, or {{param|MinAddress}},
          {{param|MaxAddress}}, or {{param|SubnetMask}} is not
          a valid value, then the table entry is inoperable and
          the CPE MUST set {{param|Status}} to
          {{enum|Error_Misconfigured|Status}}.";
          leaf Enable {
            config true;
            description
            "Enables or disables the Pool entry.";
            type boolean;
            default "false";
          }
          leaf Status {
            config false;
            description
            "The {{enum|Error}} value MAY be used by the CPE to
            indicate a locally defined error condition.";
            type enumeration {
              enum "Disabled";
              enum "Enabled";
              enum "Error_Misconfigured";
              enum "Error";
            }
            default "Disabled";
          }
          leaf Alias {
            config true;
            description
            "{{datatype|expand}}";
            type Alias;
          }
          leaf Order {
            config true;
            description
            "The value of {{param}} on creation of a {{object}}
            table entry MUST be one greater than the largest
            current value (initially assigned the lowest
            precedence).";
            type uint32 {
              range "1..max";
            }
          }
          leaf Interface {
            config true;
            description
            "{{reference}} The IP Interface associated with the
            ''Pool'' entry.";
            type string {
              length "0..256";
            }
          }
          leaf VendorClassID {
            config true;
            description
            "{{empty}} indicates this criterion is not used for
            conditional serving.";
            type string {
              length "0..255";
            }
          }
          leaf VendorClassIDExclude {
            config true;
            description
            "If {{true}}, matching packets are those that do not
            match the {{param|VendorClassID}} entry, if
            specified.";
            type boolean;
            default "false";
          }
          leaf VendorClassIDMode {
            config true;
            description
            "For example, if {{param|VendorClassID}} is
            \"Example\" then an Option 60 value of \"Example
            device\" will match with {{param}} values of
            {{enum|Prefix}} or {{enum|Substring}}, but not with
            {{enum|Exact}} or {{enum|Suffix}}.";
            type enumeration {
              enum "Exact";
              enum "Prefix";
              enum "Suffix";
              enum "Substring";
            }
            default "Exact";
          }
          leaf ClientID {
            config true;
            description
            "{{empty}} indicates this criterion is not used for
            conditional serving.";
            type yang:hex-string {
              length "0..255";
            }
          }
          leaf ClientIDExclude {
            config true;
            description
            "If {{true}}, matching packets are those that do not
            match the {{param|ClientID}} entry, if specified.";
            type boolean;
            default "false";
          }
          leaf UserClassID {
            config true;
            description
            "{{empty}} indicates this criterion is not used for
            conditional serving.";
            type yang:hex-string {
              length "0..255";
            }
          }
          leaf UserClassIDExclude {
            config true;
            description
            "If {{true}}, matching packets are those that do not
            match the {{param|UserClassID}} entry, if
            specified.";
            type boolean;
            default "false";
          }
          leaf Chaddr {
            config true;
            description
            "{{empty}} indicates this criterion is not used for
            conditional serving.";
            type yang:mac-address;
          }
          leaf ChaddrMask {
            config true;
            description
            "Bit-mask for the MAC address, where matching of a
            packet's MAC address with the {{param|Chaddr}} is
            only to be  done for bit positions set to one in
            the mask.  A mask of FF:FF:FF:FF:FF:FF  or
            {{empty}} indicates all bits of the
            {{param|Chaddr}}  are to be used for conditional
            serving classification.";
            type yang:mac-address;
          }
          leaf ChaddrExclude {
            config true;
            description
            "If {{true}}, matching packets are those that do not
            match the (masked) {{param|Chaddr}} entry, if
            specified.";
            type boolean;
            default "false";
          }
          leaf MinAddress {
            config true;
            description
            "The parameter value can be overwritten by dynamic
            values retrieved via a DHCP client with
            {{param|##.Client.{i}.PassthroughEnable}} or a PPP
            interface with
            {{param|.PPP.Interface.{i}.IPCP.PassthroughEnable}}
            equal to {{true}}.";
            type inet:ipv4-address;
          }
          leaf MaxAddress {
            config true;
            description
            "The parameter value can be overwritten by dynamic
            values retrieved via a DHCP client with
            {{param|##.Client.{i}.PassthroughEnable}} or a PPP
            interface with
            {{param|.PPP.Interface.{i}.IPCP.PassthroughEnable}}
            equal to {{true}}.";
            type inet:ipv4-address;
          }
          leaf-list ReservedAddresses {
            config true;
            description
            "{{list}} List items represent addresses marked
            reserved from the address allocation pool.";
            type inet:ipv4-address;
          }
          leaf SubnetMask {
            config true;
            description
            "The parameter value can be overwritten by dynamic
            values retrieved via a DHCP client with
            {{param|##.Client.{i}.PassthroughEnable}} or a PPP
            interface with
            {{param|.PPP.Interface.{i}.IPCP.PassthroughEnable}}
            equal to {{true}}.";
            type inet:ipv4-address;
          }
          leaf-list DNSServers {
            config true;
            description
            "The parameter value can be overwritten by dynamic
            values retrieved via a DHCP client with
            {{param|##.Client.{i}.PassthroughEnable}} or a PPP
            interface with
            {{param|.PPP.Interface.{i}.IPCP.PassthroughEnable}}
            equal to  {{true}}.";
            type inet:ipv4-address;
          }
          leaf DomainName {
            config true;
            description
            "Sets the domain name to provide to clients on the
            LAN interface.";
            type string {
              length "0..64";
            }
          }
          leaf-list IPRouters {
            config true;
            description
            "The parameter value can be overwritten by dynamic
            values retrieved via a DHCP client with
            {{param|##.Client.{i}.PassthroughEnable}} or a PPP
            interface with
            {{param|.PPP.Interface.{i}.IPCP.PassthroughEnable}}
            equal to  {{true}}.";
            type inet:ipv4-address;
          }
          leaf LeaseTime {
            config true;
            description
            "Specifies the lease time in {{units}} of client
            assigned addresses.  A value of -1 indicates an
            infinite lease.";
            type int32 {
              range "-1..max";
            }
            default "86400";
          }
          leaf StaticAddressNumberOfEntries {
            config false;
            description
            "{{numentries}}";
            type uint32;
            default "0";
          }
          leaf OptionNumberOfEntries {
            config false;
            description
            "{{numentries}}";
            type uint32;
            default "0";
          }
          leaf ClientNumberOfEntries {
            config false;
            description
            "{{numentries}}";
            type uint32;
          }
          list StaticAddress {
            key "Chaddr";
            unique "Alias";
            config true;
            description
            "Note that it is possible that an IP address in this
            table is present in one or more of the other
            conditional serving pools, in which case it is
            possible that such an address will be assigned to a
            different client.";
            leaf Enable {
              config true;
              description
              "Disabling an entry does not return the IP address
              to the pool.";
              type boolean;
              default "false";
            }
            leaf Alias {
              config true;
              description
              "{{datatype|expand}}";
              type Alias;
            }
            leaf Chaddr {
              config true;
              description
              "Hardware address (MAC address) of the physical
              interface of the DHCP client.";
              type yang:mac-address;
            }
            leaf Yiaddr {
              config true;
              description
              "IPv4 address to be assigned by the DHCP server to
              the DHCP client with the specified hardware
              address (MAC address).";
              type inet:ipv4-address;
            }
          }
          list Option {
            key "Tag";
            unique "Alias";
            config true;
            description
            "This object specifies the DHCP options that MUST,
            if enabled, be returned to clients whose DHCP
            requests are  associated with this pool.";
            leaf Enable {
              config true;
              description
              "Enables or disables this Option table entry.";
              type boolean;
              default "false";
            }
            leaf Alias {
              config true;
              description
              "{{datatype|expand}}";
              type Alias;
            }
            leaf Tag {
              config true;
              description
              "Option tag as defined in {{bibref|RFC2132}}.";
              type uint32 {
                range "1..254";
              }
            }
            leaf Value {
              config true;
              description
              "A hexbinary encoded option value.";
              type yang:hex-string {
                length "0..255";
              }
            }
          }
          list Client {
            key "Chaddr";
            unique "Alias";
            config true;
            description
            "This table lists details of DHCPv4 clients that
            matched the filter criteria of this {{object|#}}
            entry.";
            leaf Alias {
              config true;
              description
              "Note: There is no guarantee that the {{param}}
              value on automatically-created {{object}}
              instances will be retained.  This is because
              automatically-created {{object}} instances can be
              transitory.";
              type Alias;
            }
            leaf Chaddr {
              config true;
              description
              "MAC address of the DHCPv4 client.";
              type yang:mac-address;
            }
            leaf Active {
              config false;
              description
              "The ability to list inactive DHCPv4 clients is
              OPTIONAL.  If the CPE includes inactive DHCPv4
              clients in this table, {{param}} MUST be set to
              {{false}}  for each inactive DHCPv4 client.  The
              length of time an inactive DHCPv4 client remains
              listed in this table is a local matter to the
              CPE.";
              type boolean;
            }
            leaf IPv4AddressNumberOfEntries {
              config false;
              description
              "{{numentries}}";
              type uint32;
            }
            leaf OptionNumberOfEntries {
              config false;
              description
              "{{numentries}}";
              type uint32;
            }
            list IPv4Address {
              key "IPAddress";
              config false;
              description
              "IPv4 addresses assigned to this client.";
              leaf IPAddress {
                config false;
                description
                "IPv4 address.";
                type inet:ipv4-address;
              }
              leaf LeaseTimeRemaining {
                config false;
                description
                "The time at which the DHCP lease will expire or
                {{null}} if not known.  For an infinite lease,
                the parameter value MUST be
                9999-12-31T23:59:59Z.";
                type yang:date-and-time;
              }
            }
            list Option {
              key "_id";
              leaf "_id" {
                type "uint32";
              }
              config false;
              description
              "DHCPv4 options supplied by this client, e.g.
              ''VendorClassID'' (Option 60), ''ClientID''
              (option 61) or ''UserClassID'' (Option 77).";
              leaf Tag {
                config false;
                description
                "Option tag as defined in {{bibref|RFC2132}}.";
                type uint32 {
                  range "0..255";
                }
              }
              leaf Value {
                config false;
                description
                "A hexbinary encoded option value.";
                type yang:hex-string {
                  length "0..255";
                }
              }
            }
          }
        }
      }
      container Relay {
        description
        "DHCP Relay Agent (conditional relaying).";
        leaf Enable {
          config true;
          description
          "Enables or disables the DHCP Relay Agent function.";
          type boolean;
        }
        leaf Status {
          config false;
          description
          "The {{enum|Error}} value MAY be used by the CPE to
          indicate a locally defined error condition.";
          type enumeration {
            enum "Disabled";
            enum "Enabled";
            enum "Error";
          }
        }
        leaf ForwardingNumberOfEntries {
          config false;
          description
          "{{numentries}}";
          type uint32;
        }
        list Forwarding {
          key "Alias";
          config true;
          description
          "For enabled table entries, if {{param|Interface}} is
          not a valid reference then the table entry is
          inoperable and the CPE MUST set {{param|Status}} to
          {{enum|Error_Misconfigured|Status}}.";
          leaf Enable {
            config true;
            description
            "Enables or disables the Forwarding entry.";
            type boolean;
            default "false";
          }
          leaf Status {
            config false;
            description
            "The {{enum|Error}} value MAY be used by the CPE to
            indicate a locally defined error condition.";
            type enumeration {
              enum "Disabled";
              enum "Enabled";
              enum "Error_Misconfigured";
              enum "Error";
            }
            default "Disabled";
          }
          leaf Alias {
            config true;
            description
            "{{datatype|expand}}";
            type Alias;
          }
          leaf Order {
            config true;
            description
            "The value of {{param}} on creation of a {{object}}
            table entry MUST be one greater than the largest
            current value (initially assigned the lowest
            precedence).";
            type uint32 {
              range "1..max";
            }
          }
          leaf Interface {
            config true;
            description
            "{{reference}} The IP Interface associated with the
            ''Forwarding'' entry.";
            type string {
              length "0..256";
            }
          }
          leaf VendorClassID {
            config true;
            description
            "{{empty}} indicates this criterion is not used as a
            relay classification criterion.";
            type string {
              length "0..255";
            }
          }
          leaf VendorClassIDExclude {
            config true;
            description
            "If {{true}}, matching packets are those that do not
            match the {{param|VendorClassID}} entry, if
            specified.";
            type boolean;
            default "false";
          }
          leaf VendorClassIDMode {
            config true;
            description
            "For example, if {{param|VendorClassID}} is
            \"Example\" then an Option 60 value of \"Example
            device\" will match with {{param}} values of
            {{enum|Prefix}} or {{enum|Substring}}, but not with
            {{enum|Exact}} or {{enum|Suffix}}.";
            type enumeration {
              enum "Exact";
              enum "Prefix";
              enum "Suffix";
              enum "Substring";
            }
            default "Exact";
          }
          leaf ClientID {
            config true;
            description
            "{{empty}} indicates this criterion is not used as a
            relay classification criterion.";
            type yang:hex-string {
              length "0..255";
            }
          }
          leaf ClientIDExclude {
            config true;
            description
            "If {{true}}, matching packets are those that do not
            match the {{param|ClientID}} entry, if specified.";
            type boolean;
            default "false";
          }
          leaf UserClassID {
            config true;
            description
            "{{empty}} indicates this criterion is not used as a
            relay classification criterion.";
            type yang:hex-string {
              length "0..255";
            }
          }
          leaf UserClassIDExclude {
            config true;
            description
            "If {{true}}, matching packets are those that do not
            match the {{param|UserClassID}} entry, if
            specified.";
            type boolean;
            default "false";
          }
          leaf Chaddr {
            config true;
            description
            "{{empty}} indicates this criterion is not used as a
            relay classification criterion.";
            type yang:mac-address;
          }
          leaf ChaddrMask {
            config true;
            description
            "Bit-mask for the MAC address, where matching of a
            packet's MAC address with the {{param|Chaddr}} is
            only to be done for bit positions set to one in the
            mask.  A mask of FF:FF:FF:FF:FF:FF or {{empty}}
            indicates all bits of the {{param|Chaddr}} are to
            be used for relay classification.";
            type yang:mac-address;
          }
          leaf ChaddrExclude {
            config true;
            description
            "If {{true}}, matching packets are those that do not
            match the (masked) {{param|Chaddr}} entry, if
            specified.";
            type boolean;
            default "false";
          }
          leaf LocallyServed {
            config true;
            description
            "If {{true}}, incoming DHCP requests will be
            forwarded to the CPE DHCP Server.  If {{false}},
            incoming DHCP requests will be forwarded to the
            {{param|DHCPServerIPAddress}} configured for this
            forwarding entry.";
            type boolean;
            default "false";
          }
          leaf DHCPServerIPAddress {
            config true;
            description
            "IPv4 address of the DHCP server, where the request
            has to be sent to when there is a conditional match
            with this forwarding entry and
            {{param|LocallyServed}} is {{false}}. If
            {{param|LocallyServed}} is {{false}} and this
            parameter is not  configured, then the DHCP request
            is dropped.";
            type inet:ipv4-address;
          }
        }
      }
    }
    container DHCPv6 {
      description
      "The Dynamic Host Configuration Protocol (DHCP) IPv6
      object {{bibref|RFC3315}}. This entire object applies to
      IPv6 only.  It contains the {{object|Client}} and
      {{object|Server}} objects.";
      leaf ClientNumberOfEntries {
        config false;
        description
        "{{numentries}}";
        type uint32;
      }
      list Client {
        key "Interface";
        unique "Alias";
        config true;
        description
        "Note: The {{object}} table includes a unique key
        parameter that is a strong reference.  If a strongly
        referenced object is deleted, the CPE will set the
        referencing parameter to {{empty}}.  However, doing so
        under these circumstances might cause the updated
        {{object}} row to then violate the table's unique key
        constraint; if this occurs, the CPE MUST set
        {{param|Status}} to {{enum|Error_Misconfigured|Status}}
        and disable the offending {{object}} row.";
        leaf Enable {
          config true;
          description
          "Enables or disables this {{object}} entry.";
          type boolean;
          default "false";
        }
        leaf Alias {
          config true;
          description
          "{{datatype|expand}}";
          type Alias;
        }
        leaf Interface {
          config true;
          description
          "{{reference}} The IP Interface associated with the
          {{object}} entry.  This will reference an
          IPv6-capable interface (that is attached to the IPv6
          stack), otherwise the table entry will be inoperable.";
          type string {
            length "0..256";
          }
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf DUID {
          config false;
          description
          "The client's DHCP Unique Identifier (DUID)
          {{bibref|RFC3315|Section 9}}. {{param}} is set by the
          CPE.";
          type yang:hex-string {
            length "0..130";
          }
        }
        leaf RequestAddresses {
          config true;
          description
          "Enables or disables inclusion of the ''Identity
          Association (IA) for Non-Temporary Address'' option
          OPTION_IA_NA(3) {{bibref|RFC3315|Section 22.4}} in
          Solicit messages.";
          type boolean;
          default "true";
        }
        leaf RequestPrefixes {
          config true;
          description
          "Note that this is only appropriate for an upstream
          interface on a requesting router, e.g.  for an RG WAN
          interface.";
          type boolean;
          default "false";
        }
        leaf RapidCommit {
          config true;
          description
          "Enables or disables inclusion of the ''Rapid Commit''
          option OPTION_RAPID_COMMIT(14)
          {{bibref|RFC3315|Section 22.14}} in Solicit messages.";
          type boolean;
          default "false";
        }
        leaf Renew {
          config true;
          description
          "When set to {{true}}, the {{object}} will renew its
          DHCPv6-supplied information (i.e.  the CPE will do a
          renew or information request as needed, updating both
          stateful and stateless parameter values discovered by
          this Client instance).";
          type boolean;
          default "false";
        }
        leaf SuggestedT1 {
          config true;
          description
          "A value of -1 indicates that no T1 value is
          specified.";
          type int32 {
            range "-1..max";
          }
        }
        leaf SuggestedT2 {
          config true;
          description
          "A value of -1 indicates that no T2 value is
          specified.";
          type int32 {
            range "-1..max";
          }
        }
        leaf-list SupportedOptions {
          config false;
          description
          "{{list}} The options that the client is able to
          process in server responses.  This list MUST include
          both top-level and encapsulated options, e.g.  if the
          client is able to process OPTION_IA_NA (3) with an
          encapsulated OPTION_IAADDR (5), the list would be
          expected to include both 3 and 5.";
          type uint32;
        }
        leaf-list RequestedOptions {
          config true;
          description
          "Loosely speaking, these are the options that the
          client will include in OPTION_ORO {{bibref|RFC3315}}
          but the client is free to decide (in accordance with
          {{bibref|RFC3315}}) in which messages to request
          which option, whether also to request additional
          options, whether not to request inappropriate
          options, and in which order to request any options
          that are also in {{param|SupportedOptions}}.";
          type uint32;
        }
        leaf ServerNumberOfEntries {
          config false;
          description
          "{{numentries}}";
          type uint32;
        }
        leaf SentOptionNumberOfEntries {
          config false;
          description
          "{{numentries}}";
          type uint32;
        }
        leaf ReceivedOptionNumberOfEntries {
          config false;
          description
          "{{numentries}}";
          type uint32;
        }
        list Server {
          key "SourceAddress";
          config false;
          description
          "This is a transitory table that lists the discovered
          DHCPv6 servers (it does ''not'' model a local DHCP
          server). Table entries are automatically created to
          correspond with these servers.  However, it is a
          local matter to the CPE when to delete old table
          entries.";
          leaf SourceAddress {
            config false;
            description
            "The IP address from which the message most recently
            received from this server was sent.";
            type inet:ipv6-address;
          }
          leaf DUID {
            config false;
            description
            "The server's DHCP Unique Identifier (DUID)
            {{bibref|RFC3315|Section 9}} as received via
            OPTION_SERVERID.";
            type yang:hex-string {
              length "0..130";
            }
          }
          leaf InformationRefreshTime {
            config false;
            description
            "The OPTION_INFORMATION_REFRESH_TIME value
            {{bibref|RFC4242}} that was most recently received
            from this server, converted to the ''dateTime'' at
            which the associated information will expire.  If
            no such option has been received, the parameter
            value MUST be the \"Unknown Time\" {{null}}.  If
            the information will never expire, the parameter
            value MUST be infinite time 9999-12-31T23:59:59Z.";
            type yang:date-and-time;
          }
        }
        list SentOption {
          key "Tag";
          unique "Alias";
          config true;
          description
          "This table is intended only for options that are not
          part of the basic operation of the protocol, and
          whose values are simple, do not often change and are
          not modeled elsewhere.  For example, it is
          appropriate for OPTION_USER_CLASS (whose value is a
          list of user classes) but is not appropriate for
          OPTION_RECONF_MSG (which is part of the protocol),
          OPTION_IA_NA (which is modeled via
          {{param|#.RequestAddresses}}) or OPTION_RAPID_COMMIT
          (which is modeled via {{param|#.RapidCommit}}).";
          leaf Enable {
            config true;
            description
            "Enables or disables this {{object}} entry.";
            type boolean;
            default "false";
          }
          leaf Alias {
            config true;
            description
            "{{datatype|expand}}";
            type Alias;
          }
          leaf Tag {
            config true;
            description
            "Option tag (code) {{bibref|RFC3315|Section 22.1}}.";
            type uint32 {
              range "0..65535";
            }
          }
          leaf Value {
            config true;
            description
            "Note: The length of the option data is
            ''option-len'' octets, as specified in
            {{bibref|RFC3315|Section 22.1}}.";
            type yang:hex-string {
              length "0..65535";
            }
          }
        }
        list ReceivedOption {
          key "_id";
          leaf "_id" {
            type "uint32";
          }
          config false;
          description
          "If the same option is received multiple times,
          whether from one or more servers, it is up to the CPE
          to decide which entries to include (i.e.  whether the
          same option will be present multiple times). In order
          to allow for the same option to be present multiple
          times within the table, this table has no unique key
          defined.";
          leaf Tag {
            config false;
            description
            "Option tag (code) {{bibref|RFC3315|Section 22.1}}.";
            type uint32 {
              range "0..65535";
            }
          }
          leaf Value {
            config false;
            description
            "A hexbinary encoded option data
            {{bibref|RFC3315|Section 22.1}}.";
            type yang:hex-string {
              length "0..65535";
            }
          }
          leaf Server {
            config false;
            description
            "{{reference}} This is the server that sent the
            option to the client.  Each {{object}} entry MUST
            have an associated server.";
            type string;
          }
        }
      }
      container Server {
        description
        "DHCPv6 server configuration.";
        leaf Enable {
          config true;
          description
          "Enables or disables the DHCPv6 server function.";
          type boolean;
        }
        leaf PoolNumberOfEntries {
          config false;
          description
          "{{numentries}}";
          type uint32;
        }
        list Pool {
          key "Order";
          unique "Alias";
          config true;
          description
          "For enabled table entries, if {{param|Interface}} is
          not a valid reference to an IPv6-capable interface
          (that is attached to the IPv6 stack) then the table
          entry is inoperable and the CPE MUST set
          {{param|Status}} to
          {{enum|Error_Misconfigured|Status}}.";
          leaf Enable {
            config true;
            description
            "Enables or disables this {{object}} entry.";
            type boolean;
            default "false";
          }
          leaf Status {
            config false;
            description
            "The {{enum|Error}} value MAY be used by the CPE to
            indicate a locally defined error condition.";
            type enumeration {
              enum "Disabled";
              enum "Enabled";
              enum "Error_Misconfigured";
              enum "Error";
            }
            default "Disabled";
          }
          leaf Alias {
            config true;
            description
            "{{datatype|expand}}";
            type Alias;
          }
          leaf Order {
            config true;
            description
            "The value of {{param}} on creation of a {{object}}
            table entry MUST be one greater than the largest
            current value (initially assigned the lowest
            precedence).";
            type uint32 {
              range "1..max";
            }
          }
          leaf Interface {
            config true;
            description
            "{{reference}} The IP Interface associated with the
            {{object}} entry.";
            type string {
              length "0..256";
            }
          }
          leaf DUID {
            config true;
            description
            "Note: DHCPv6 Option 1 (DUID) is sometimes referred
            to as ''Client Identifier''.";
            type yang:hex-string {
              length "0..130";
            }
          }
          leaf DUIDExclude {
            config true;
            description
            "If {{true}}, matching packets are those that do not
            match the {{param|DUID}} entry, if specified.";
            type boolean;
            default "false";
          }
          leaf VendorClassID {
            config true;
            description
            "{{empty}} indicates this criterion is not used.";
            type yang:hex-string {
              length "0..65535";
            }
          }
          leaf VendorClassIDExclude {
            config true;
            description
            "If {{true}}, matching packets are those that do not
            match the {{param|VendorClassID}} entry, if
            specified.";
            type boolean;
            default "false";
          }
          leaf UserClassID {
            config true;
            description
            "{{empty}} indicates this criterion is not used.";
            type yang:hex-string {
              length "0..65535";
            }
          }
          leaf UserClassIDExclude {
            config true;
            description
            "If {{true}}, matching packets are those that do not
            match the {{param|UserClassID}} entry, if
            specified.";
            type boolean;
            default "false";
          }
          leaf SourceAddress {
            config true;
            description
            "{{empty}} indicates this criterion is not used for
            serving.";
            type inet:ipv6-address;
          }
          leaf SourceAddressMask {
            config true;
            description
            "Bit-mask for the source address, where matching of
            a packet's source address with the
            {{param|SourceAddress}} is only to be done for bit
            positions set to one in the mask.  A mask of
            {{empty}} indicates all bits of the
            {{param|SourceAddress}} are to be used.";
            type inet:ipv6-address;
          }
          leaf SourceAddressExclude {
            config true;
            description
            "If {{true}}, matching packets are those that do not
            match the (masked) {{param|SourceAddress}} entry,
            if specified.";
            type boolean;
            default "false";
          }
          leaf IANAEnable {
            config true;
            description
            "Enables or disables IANA offers.";
            type boolean;
          }
          leaf-list IANAManualPrefixes {
            config true;
            description
            "Prefixes MUST be associated with the interface
            instance referenced by {{param|Interface}}.";
            type string;
          }
          leaf-list IANAPrefixes {
            config false;
            description
            "* Prefixes with
            {{param|.IP.Interface.{i}.IPv6Prefix.{i}.Origin}} =
            {{enum|Child|.IP.Interface.{i}.IPv6Prefix.{i}.Origin}}
            or
            {{enum|AutoConfigured|.IP.Interface.{i}.IPv6Prefix.{i}.Origin}}
            associated with the interface instance referenced
            by {{param|Interface}}.";
            type string;
          }
          leaf IAPDEnable {
            config true;
            description
            "Enables or disables IAPD offers.";
            type boolean;
          }
          leaf-list IAPDManualPrefixes {
            config true;
            description
            "All clients that request IA_PD and match filter
            criteria on this {{param|Interface}} MUST be
            offered IA_PD prefixes derived from all of the
            ''Valid''
            ({{param|.IP.Interface.{i}.IPv6Prefix.{i}.ValidLifetime}}
            is infinite or in the future) prefixes in this
            list.";
            type string;
          }
          leaf-list IAPDPrefixes {
            config false;
            description
            "* Prefixes with
            {{param|.IP.Interface.{i}.IPv6Prefix.{i}.Origin}} =
            {{enum|Child|.IP.Interface.{i}.IPv6Prefix.{i}.Origin}}
            or
            {{enum|AutoConfigured|.IP.Interface.{i}.IPv6Prefix.{i}.Origin}}
            associated with the interface instance referenced
            by {{param|Interface}}.";
            type string;
          }
          leaf IAPDAddLength {
            config true;
            description
            "The RECOMMENDED minimum number of bits to add to
            {{param|IAPDManualPrefixes}} or
            {{param|IAPDPrefixes}} in order to determine the
            length of prefixes that are offered in an IA_PD.
            The device is responsible for ensuring that it does
            not delegate a prefix longer than /64.  The device
            can have additional logic that is used (in
            conjunction with this parameter) to determine the
            actual length of prefixes offered in an IA_PD.";
            type uint32 {
              range "min..64";
            }
          }
          leaf ClientNumberOfEntries {
            config false;
            description
            "{{numentries}}";
            type uint32;
            default "0";
          }
          leaf OptionNumberOfEntries {
            config false;
            description
            "{{numentries}}";
            type uint32;
            default "0";
          }
          list Client {
            key "SourceAddress";
            unique "Alias";
            config true;
            description
            "This table lists details of DHCPv6 clients that
            matched the filter criteria of this {{object|#}}
            entry.";
            leaf Alias {
              config true;
              description
              "Note: There is no guarantee that the {{param}}
              value on automatically-created {{object}}
              instances will be retained.  This is because
              automatically-created {{object}} instances can be
              transitory.";
              type Alias;
            }
            leaf SourceAddress {
              config true;
              description
              "Source address of the DHCPv6 client.";
              type inet:ipv6-address;
            }
            leaf Active {
              config false;
              description
              "The ability to list inactive DHCPv6 clients is
              OPTIONAL.  If the CPE includes inactive DHCPv6
              clients in this table, {{param}} MUST be set to
              {{false}}  for each inactive DHCPv6 client.  The
              length of time an inactive DHCPv6 client remains
              listed in this table is a local matter to the
              CPE.";
              type boolean;
            }
            leaf IPv6AddressNumberOfEntries {
              config false;
              description
              "{{numentries}}";
              type uint32;
            }
            leaf IPv6PrefixNumberOfEntries {
              config false;
              description
              "{{numentries}}";
              type uint32;
            }
            leaf OptionNumberOfEntries {
              config false;
              description
              "{{numentries}}";
              type uint32;
            }
            list IPv6Address {
              key "IPAddress";
              config false;
              description
              "IPv6 addresses assigned to this client via IA_NA.";
              leaf IPAddress {
                config false;
                description
                "IPv6 address.";
                type inet:ipv6-address;
              }
              leaf PreferredLifetime {
                config false;
                description
                "The time at which this address will cease to be
                preferred (i.e.  will become deprecated), or
                {{null}} if not known.  For an infinite
                lifetime, the parameter value MUST be
                9999-12-31T23:59:59Z.";
                type yang:date-and-time;
              }
              leaf ValidLifetime {
                config false;
                description
                "The time at which this address will cease to be
                valid (i.e.  will become invalid), or {{null}}
                if unknown.  For an infinite lifetime, the
                parameter value MUST be 9999-12-31T23:59:59Z.";
                type yang:date-and-time;
              }
            }
            list IPv6Prefix {
              key "Prefix";
              config false;
              description
              "IPv6 prefixes delegated to this client via IA_PD.";
              leaf Prefix {
                config false;
                description
                "IPv6 address prefix.";
                type inet:ipv6-prefix;
              }
              leaf PreferredLifetime {
                config false;
                description
                "The time at which this prefix will cease to be
                preferred (i.e.  will become deprecated), or
                {{null}} if not known.  For an infinite
                lifetime, the parameter value MUST be
                9999-12-31T23:59:59Z.";
                type yang:date-and-time;
              }
              leaf ValidLifetime {
                config false;
                description
                "The time at which this prefix will cease to be
                valid (i.e.  will become invalid), or {{null}}
                if unknown.  For an infinite lifetime, the
                parameter value MUST be 9999-12-31T23:59:59Z.";
                type yang:date-and-time;
              }
            }
            list Option {
              key "_id";
              leaf "_id" {
                type "uint32";
              }
              config false;
              description
              "DHCPv6 options supplied by this client, e.g.
              ''DUID'' (Option 1), ''UserClassID'' (Option 15)
              or ''VendorClassID'' (option 16).";
              leaf Tag {
                config false;
                description
                "Option tag (code) {{bibref|RFC3315|Section
                22.1}}.";
                type uint32 {
                  range "0..65535";
                }
              }
              leaf Value {
                config false;
                description
                "A hexbinary encoded option value.";
                type yang:hex-string {
                  length "0..65535";
                }
              }
            }
          }
          list Option {
            key "Tag";
            unique "Alias";
            config true;
            description
            "This object specifies the DHCPv6 options that MUST,
            if enabled, be offered to clients whose DHCPv6
            requests are associated with this pool.  If
            {{param|PassthroughClient}} is specified, and the
            referenced client has a value for a given option
            then the {{param|PassthroughClient}} option value
            will be sent instead of {{param|Value}}. Otherwise,
            {{param|Value}} will be sent.";
            leaf Enable {
              config true;
              description
              "Enables or disables this {{object}} entry.";
              type boolean;
              default "false";
            }
            leaf Alias {
              config true;
              description
              "{{datatype|expand}}";
              type Alias;
            }
            leaf Tag {
              config true;
              description
              "Option tag (code) {{bibref|RFC3315|Section
              22.1}}.";
              type uint32 {
                range "0..65535";
              }
            }
            leaf Value {
              config true;
              description
              "A hexbinary encoded option value.";
              type yang:hex-string {
                length "0..65535";
              }
            }
            leaf PassthroughClient {
              config true;
              description
              "{{empty}} indicates that passthrough is not
              configured for this {{object}} entry.";
              type string {
                length "0..256";
              }
            }
          }
        }
      }
    }
    container IEEE8021x {
      description
      "IEEE 802.1x object {{bibref|802.1x-2004}}, where
      {{object|Supplicant}} models authentication supplicants.";
      leaf SupplicantNumberOfEntries {
        config false;
        description
        "{{numentries}}";
        type uint32;
      }
      list Supplicant {
        key "Interface";
        unique "Alias";
        config true;
        description
        "Note: The {{object}} table includes a unique key
        parameter that is a strong reference.  If a strongly
        referenced object is deleted, the CPE will set the
        referencing parameter to {{empty}}. However, doing so
        under these circumstances might cause the updated
        {{object}} row to then violate the table's unique key
        constraint; if this occurs, the CPE MUST set
        {{param|Status}} to {{enum|Error_Misconfigured|Status}}
        and disable the offending {{object}} row.";
        leaf Enable {
          config true;
          description
          "This parameter controls whether this resource will
          utilize the 802.1x protocol as a supplicant for
          device  authentication purposes.";
          type boolean;
          default "false";
        }
        leaf Status {
          config false;
          description
          "The {{enum|Error}} value MAY be used by the CPE to
          indicate a locally defined error condition.";
          type enumeration {
            enum "Disabled";
            enum "Enabled";
            enum "Error_Misconfigured";
            enum "Error";
          }
          default "Disabled";
        }
        leaf Alias {
          config true;
          description
          "{{datatype|expand}}";
          type Alias;
        }
        leaf Interface {
          config true;
          description
          "{{reference}} The interface on which authentication
          is to be performed.  Example:  Device.Ethernet.Link.1";
          type string {
            length "0..256";
          }
        }
        leaf PAEState {
          config false;
          description
          "The current supplicant state machine as defined in
          {{bibref|802.1x-2004|9.5.1}}, Supplicant PAE (Port
          Access Entity) State.  {{enum}}";
          type enumeration {
            enum "Disconnected";
            enum "Logoff";
            enum "Connecting";
            enum "Authenticating";
            enum "Authenticated";
            enum "Held";
            enum "Restart";
            enum "ForceAuth";
            enum "ForceUnauth";
          }
        }
        leaf EAPIdentity {
          config true;
          description
          "The identity to be exchanged between the supplicant
          and authenticator.";
          type string {
            length "0..256";
          }
        }
        leaf MaxStart {
          config true;
          description
          "This is in support of {{bibref|802.1x-2004|Section
          8.4.6}}, Migration Considerations.";
          type uint32 {
            range "1..10";
          }
        }
        leaf StartPeriod {
          config true;
          description
          "The period in {{units}} a supplicant will wait before
          the device will attempt to re-send an EAP start
          message as defined in {{bibref|802.1x-2004|9.5.1}},
          startPeriod.";
          type uint32 {
            range "1..max";
          }
        }
        leaf HeldPeriod {
          config true;
          description
          "The hold-off period in {{units}} a supplicant will
          wait before re-attempting authentication as defined
          in {{bibref|802.1x-2004|9.5.1}}, heldPeriod.";
          type uint32 {
            range "1..max";
          }
        }
        leaf AuthPeriod {
          config true;
          description
          "The period in {{units}} after which a request will be
          considered timed out as defined in
          {{bibref|802.1x-2004|9.5.1}}, authPeriod.";
          type uint32;
        }
        leaf-list AuthenticationCapabilities {
          config false;
          description
          "{{list}} Indicates the authentication methods
          supported by the device.  {{enum}}";
          type enumeration {
            enum "EAP-TLS";
            enum "EAP-MD5";
          }
        }
        leaf StartFailurePolicy {
          config true;
          description
          "This is in support of {{bibref|802.1x-2004|Section
          8.4.6}}, Migration Considerations.";
          type enumeration {
            enum "FailAuthentication";
            enum "AssumeAuthentication";
          }
        }
        leaf AuthenticationSuccessPolicy {
          config true;
          description
          "The action to be taken when authentication succeeds
          and a connection has already received an address
          and/or policy settings.  {{enum}}";
          type enumeration {
            enum "NoAction";
            enum "RenewConnection";
          }
        }
        leaf Reset {
          config true;
          description
          "The device MUST initiate the reset after completion
          of the current CWMP session.  The device MAY delay
          resetting the resource in  order to avoid
          interruption of a user service such as an ongoing
          voice call.";
          type boolean;
        }
        leaf Disconnect {
          config true;
          description
          "The device MUST initiate the disconnect after
          completion of the current CWMP session.  The device
          MAY delay re-authentication of the  resource in order
          to avoid interruption of a user service such as an
          ongoing voice call.";
          type boolean;
        }
        container Stats {
          description
          "802.1x Authentication Supplicant EAP statistics
          information for this resource.";
          leaf ReceivedFrames {
            config false;
            description
            "The number of EAPOL frames of any type that have
            been received by this Supplicant;
            {{bibref|802.1x-2004|9.5.2}}, EAPOL frames
            received.";
            type uint32;
            default "0";
          }
          leaf TransmittedFrames {
            config false;
            description
            "The number of EAPOL frames of any type that have
            been transmitted by this Supplicant;
            {{bibref|802.1x-2004|9.5.2}}, EAPOL frames
            transmitted.";
            type uint32;
            default "0";
          }
          leaf TransmittedStartFrames {
            config false;
            description
            "The number of EAPOL Start frames that have been
            transmitted by this Supplicant;
            {{bibref|802.1x-2004|9.5.2}}, EAPOL Start frames
            transmitted.";
            type uint32;
            default "0";
          }
          leaf TransmittedLogoffFrames {
            config false;
            description
            "The number of EAPOL Logoff frames that have been
            transmitted by this Supplicant;
            {{bibref|802.1x-2004|9.5.2}}, EAPOL Logoff frames
            transmitted.";
            type uint32;
            default "0";
          }
          leaf TransmittedResponseIdFrames {
            config false;
            description
            "The number of EAP Resp/Id frames that have been
            transmitted; {{bibref|802.1x-2004|9.5.2}}, EAP
            Resp/Id frames transmitted.";
            type uint32;
            default "0";
          }
          leaf TransmittedResponseFrames {
            config false;
            description
            "The number of valid EAP Response frames (other than
            Resp/Id frames) that have been transmitted by this
            Supplicant; {{bibref|802.1x-2004|9.5.2}}, EAP Resp
            frames transmitted.";
            type uint32;
            default "0";
          }
          leaf ReceivedRequestIdFrames {
            config false;
            description
            "The number of EAP Req/Id frames that have been
            received by this Supplicant;
            {{bibref|802.1x-2004|9.5.2}}, EAP Req/Id frames
            received.";
            type uint32;
            default "0";
          }
          leaf ReceivedRequestFrames {
            config false;
            description
            "The number of EAP Request frames (other than Rq/Id
            frames) that have been received by this Supplicant;
            {{bibref|802.1x-2004|9.5.2}}, EAP Req frames
            received.";
            type uint32;
            default "0";
          }
          leaf ReceivedInvalidFrames {
            config false;
            description
            "The number of EAPOL frames that have been received
            by this Supplicant in which the frame type is not
            recognized; {{bibref|802.1x-2004|9.5.2}}, EAP Req
            frames received.";
            type uint32;
            default "0";
          }
          leaf ReceivedLengthErrorFrames {
            config false;
            description
            "The number of EAPOL frames that have been received
            by this Supplicant in which the Packet Body Length
            field is invalid; {{bibref|802.1x-2004|9.5.2}}, EAP
            length error frames received.";
            type uint32;
            default "0";
          }
          leaf LastFrameVersion {
            config false;
            description
            "The protocol version number carried in the most
            recently received EAPOL frame;
            {{bibref|802.1x-2004|9.5.2}}, Last EAPOL frame
            version";
            type uint32;
          }
          leaf LastFrameSourceMACAddress {
            config false;
            description
            "The source MAC address carried in the most recently
            received EAPOL frame; {{bibref|802.1x-2004|9.5.2}},
            Last EAPOL frame source.";
            type yang:mac-address;
          }
        }
        container EAPMD5 {
          description
          "802.1x Authentication Supplicant provisioning
          information used for MD5 shared secret exchange.
          This object will not exist if EAP-MD5 is not a
          supported authentication type.";
          leaf Enable {
            config true;
            description
            "This parameter enables or disables the supplicant's
            support for EAP-MD5.";
            type boolean;
          }
          leaf SharedSecret {
            config true;
            description
            "The shared secret to be exchanged between the
            supplicant and authenticator.";
            type string {
              length "0..256";
            }
          }
        }
        container EAPTLS {
          description
          "802.1x Authentication Supplicant provisioning
          information used for TLS certificate authentication.
          This object will not exist if the EAP-TLS is not a
          supported authentication type.";
          leaf Enable {
            config true;
            description
            "This parameter enables or disables the supplicant's
            support for EAP-TLS.";
            type boolean;
          }
          leaf MutualAuthenticationEnable {
            config true;
            description
            "The parameter controls if the supplicant will
            authenticate the authenticator.";
            type boolean;
          }
        }
      }
    }
    container Users {
      description
      "Users object that contains the {{object|User}} table.";
      leaf UserNumberOfEntries {
        config false;
        description
        "{{numentries}}";
        type uint32;
      }
      list User {
        key "Username";
        unique "Alias";
        config true;
        description
        "This object contains parameters relating to the user
        characteristics.";
        leaf Alias {
          config true;
          description
          "{{datatype|expand}}";
          type Alias;
        }
        leaf Enable {
          config true;
          description
          "If the User being configured is currently accessing
          the device then a disable MUST apply to the next user
          session and the current user session MUST NOT be
          abruptly terminated.";
          type boolean;
          default "false";
        }
        leaf RemoteAccessCapable {
          config true;
          description
          "Allows this user to remotely access the UserInterface
          via the mechanism defined in
          {{object|.UserInterface.RemoteAccess.}}";
          type boolean;
          default "false";
        }
        leaf Username {
          config true;
          description
          "Name of the current user.  MUST NOT be {{empty}} for
          an enabled entry.";
          type string {
            length "0..64";
          }
        }
        leaf Password {
          config true;
          description
          "The user's password.";
          type string {
            length "0..64";
          }
        }
        leaf Language {
          config true;
          description
          "If {{empty}},
          {{param|.UserInterface.CurrentLanguage}} is used.";
          type string {
            length "0..16";
          }
        }
      }
    }
    container SmartCardReaders {
      description
      "SmartCardReaders object that contains the
      {{object|SmartCardReader}} table.";
      leaf SmartCardReaderNumberOfEntries {
        config false;
        description
        "{{numentries}}";
        type uint32;
      }
      list SmartCardReader {
        key "Name";
        unique "Alias";
        config true;
        description
        "This object describes the characteristics of the smart
        card reader.";
        leaf Alias {
          config true;
          description
          "{{datatype|expand}}";
          type Alias;
        }
        leaf Enable {
          config true;
          description
          "Enables or disables this smart card reader.";
          type boolean;
        }
        leaf Status {
          config false;
          description
          "Indicates the status of this smart card reader.";
          type enumeration {
            enum "Disabled";
            enum "Enabled" {
              description
              "Indicates the smart card reader is enabled and
              functioning properly.";
            }
            enum "Error" {
              description
              "Indicates the smart card reader is enabled and
              not functioning properly.";
            }
          }
        }
        leaf Name {
          config true;
          description
          "Human-readable name associated with this smart card
          reader.";
          type string {
            length "0..256";
          }
        }
        leaf Reset {
          config true;
          description
          "When set to {{true}}, resets the SmartCard Reader and
          the associated SmartCard.";
          type boolean;
        }
        leaf ResetTime {
          config false;
          description
          "Unknown Time value indicates that this SmartCard
          Reader has never been reset, which can only happen if
          it has never been enabled.";
          type yang:date-and-time;
        }
        leaf DecryptionFailedCounter {
          config false;
          description
          "This counter relates to the smart card reader, not to
          the smart card itself, i.e.  it is reset when the
          {{param|Reset}} parameter is used and not when a
          Smart Card is inserted or removed.";
          type uint32;
        }
        leaf DecryptionFailedNoKeyCounter {
          config false;
          description
          "This counter relates to the smart card reader, not to
          the smart card itself, i.e.  it is reset when the
          {{param|Reset}} parameter is used and not when a
          Smart Card is inserted or removed.";
          type uint32;
        }
        container SmartCard {
          description
          "Status of currently associated smart card.";
          leaf Status {
            config false;
            description
            "Status of the Smart Card.";
            type enumeration {
              enum "None" {
                description
                "Indicates that no Smart Card is inserted.";
              }
              enum "Running" {
                description
                "Indicates a Smart Card is present and working
                normally.";
              }
              enum "Error" {
                description
                "Indicates the Smart Card is present and in an
                error condition.";
              }
            }
          }
          leaf Type {
            config false;
            description
            "Vendors can extend the enumerated values with
            vendor specific extensions, in which case the rules
            outlined in {{bibref|TR-106a2|Section 3.3}} MUST be
            adhered to.";
            type enumeration {
              enum "CA";
              enum "DRM";
              enum "UICC";
            }
          }
          leaf-list Application {
            config false;
            description
            "Vendors can extend the enumerated values with
            vendor specific extensions, in which case the rules
            outlined in {{bibref|TR-106a2|Section 3.3}} MUST be
            adhered to.";
            type enumeration {
              enum "SIM";
              enum "USIM";
              enum "ISIM";
            }
          }
          leaf SerialNumber {
            config false;
            description
            "The Smart Card Serial Number or {{empty}} if the
            Smart Card serial Number is not available, e.g.  in
            the case of IPTV due to restrictions of the Service
            Delivery Platform.";
            type string {
              length "0..256";
            }
          }
          leaf ATR {
            config false;
            description
            "The Smart Card answer to a reset action.  Issued by
            the Smart Card upon reset.";
            type string {
              length "0..1024";
            }
          }
        }
      }
    }
    container UPnP {
      description
      "This object contains all UPnP related objects and
      parameters including Device and Discovery related objects
      and parameters.";
      container Device {
        description
        "This object defines the UPnP devices and UPnP services
        that are implemented by the CPE.";
        leaf Enable {
          config true;
          description
          "Enables/Disables UPnP support.";
          type boolean;
        }
        leaf UPnPMediaServer {
          config true;
          description
          "Enables/Disables UPnP Media Server.";
          type boolean;
        }
        leaf UPnPMediaRenderer {
          config true;
          description
          "Enables/Disables UPnP Media Renderer.";
          type boolean;
        }
        leaf UPnPWLANAccessPoint {
          config true;
          description
          "Enables/Disables UPnP Wireless Access Point.";
          type boolean;
        }
        leaf UPnPQoSDevice {
          config true;
          description
          "Enables/Disables UPnP QoS Device.";
          type boolean;
        }
        leaf UPnPQoSPolicyHolder {
          config true;
          description
          "Enables/Disables UPnP QoS Policy Holder.";
          type boolean;
        }
        leaf UPnPIGD {
          config true;
          description
          "Enables/Disables UPnP IGD.";
          type boolean;
        }
        leaf UPnPDMBasicMgmt {
          config true;
          description
          "Enables/Disables UPnP-DM Basic Management.";
          type boolean;
        }
        leaf UPnPDMConfigurationMgmt {
          config true;
          description
          "Enables/Disables UPnP-DM Configuration Management.";
          type boolean;
        }
        leaf UPnPDMSoftwareMgmt {
          config true;
          description
          "Enables/Disables UPnP-DM Software Management.";
          type boolean;
        }
        container Capabilities {
          description
          "This object defines what UPnP capabilities this
          device has.";
          leaf UPnPArchitecture {
            config false;
            description
            "A value of 0 indicates no UPnP support.";
            type uint32;
          }
          leaf UPnPArchitectureMinorVer {
            config false;
            description
            "If {{param|UPnPArchitecture}} is 0 then this
            parameter SHOULD be ignored.";
            type uint32;
          }
          leaf UPnPMediaServer {
            config false;
            description
            "A value of 0 indicates no support.";
            type uint32;
          }
          leaf UPnPMediaRenderer {
            config false;
            description
            "A value of 0 indicates no support.";
            type uint32;
          }
          leaf UPnPWLANAccessPoint {
            config false;
            description
            "A value of 0 indicates no support.";
            type uint32;
          }
          leaf UPnPBasicDevice {
            config false;
            description
            "A value of 0 indicates no support.";
            type uint32;
          }
          leaf UPnPQoSDevice {
            config false;
            description
            "A value of 0 indicates no support.";
            type uint32;
          }
          leaf UPnPQoSPolicyHolder {
            config false;
            description
            "A value of 0 indicates no support.";
            type uint32;
          }
          leaf UPnPIGD {
            config false;
            description
            "A value of 0 indicates no support.";
            type uint32;
          }
          leaf UPnPDMBasicMgmt {
            config false;
            description
            "A value of 0 indicates no support.";
            type uint32;
          }
          leaf UPnPDMConfigurationMgmt {
            config false;
            description
            "A value of 0 indicates no support.";
            type uint32;
          }
          leaf UPnPDMSoftwareMgmt {
            config false;
            description
            "A value of 0 indicates no support.";
            type uint32;
          }
        }
      }
      container Discovery {
        description
        "The CPE MAY, but need not, retain some or all of the
        information in this object across reboots.";
        leaf RootDeviceNumberOfEntries {
          config false;
          description
          "{{numentries}}";
          type uint32;
        }
        leaf DeviceNumberOfEntries {
          config false;
          description
          "{{numentries}}";
          type uint32;
        }
        leaf ServiceNumberOfEntries {
          config false;
          description
          "{{numentries}}";
          type uint32;
        }
        list RootDevice {
          key "UUID";
          config false;
          description
          "UPnP root device table.  This table contains an entry
          for each UPnP root device that has been discovered
          via SSDP.";
          leaf Status {
            config false;
            description
            "The ability to list inactive UPnP root devices is
            OPTIONAL. The length of time an inactive device
            remains listed in this table is a local matter to
            the CPE.";
            type enumeration {
              enum "LeaseActive" {
                description
                "Device is active and UPnP lease has not
                expired.";
              }
              enum "LeaseExpired" {
                description
                "Device is inactive because UPnP lease has
                expired.";
              }
              enum "ByebyeReceived" {
                description
                "Device is inactive because byebye message was
                received.";
              }
            }
          }
          leaf UUID {
            config false;
            description
            "{{pattern}}";
            type string {
              length "0..36";
              pattern "[0-9A-Fa-f]{8}-([0-9A-Fa-f]{4}-){3}[0-9A-Fa-f]{12}";
            }
          }
          leaf USN {
            config false;
            description
            ": ''uuid:device-UUID'' (for root device UUID)";
            type string {
              length "0..256";
            }
          }
          leaf LeaseTime {
            config false;
            description
            "The UPnP root device lease time in {{units}},
            extracted from the CACHE-CONTROL header.";
            type uint32;
          }
          leaf Location {
            config false;
            description
            "The value of the LOCATION header for this UPnP root
            device, which is the URL of the root device's DDD
            (Device Description Document).";
            type string {
              length "0..256";
            }
          }
          leaf Server {
            config false;
            description
            "where '''UPnP''' is a literal string,
            '''udaversion''' is the version of the UPnP Device
            Architecture.";
            type string {
              length "0..256";
            }
          }
          leaf-list Host {
            config false;
            description
            "As such entries are added to or removed from the
            Host tables, the value of this parameter MUST be
            updated accordingly.";
            type string {
              length "0..256";
            }
          }
          leaf LastUpdate {
            config false;
            description
            "The date and time at which the last advertisement
            from this {{object}} was received.";
            type yang:date-and-time;
          }
        }
        list Device {
          key "UUID";
          config false;
          description
          "UPnP embedded device table.  This table contains an
          entry for each UPnP embedded device that has been
          discovered via SSDP.";
          leaf Status {
            config false;
            description
            "The ability to list inactive UPnP embedded devices
            is OPTIONAL. The length of time an inactive device
            remains listed in this table is a local matter to
            the CPE.";
            type enumeration {
              enum "LeaseActive" {
                description
                "Device is active and UPnP lease has not
                expired.";
              }
              enum "LeaseExpired" {
                description
                "Device is inactive because UPnP lease has
                expired.";
              }
              enum "ByebyeReceived" {
                description
                "Device is inactive because byebye message was
                received.";
              }
            }
          }
          leaf UUID {
            config false;
            description
            "{{pattern}}";
            type string {
              length "0..36";
              pattern "[0-9A-Fa-f]{8}-([0-9A-Fa-f]{4}-){3}[0-9A-Fa-f]{12}";
            }
          }
          leaf USN {
            config false;
            description
            ": ''uuid:device-UUID''";
            type string {
              length "0..256";
            }
          }
          leaf LeaseTime {
            config false;
            description
            "The UPnP embedded device lease time in {{units}},
            extracted from the CACHE-CONTROL header.";
            type uint32;
          }
          leaf Location {
            config false;
            description
            "The value of the LOCATION header for this UPnP
            embedded device, which is the URL of the root
            device's DDD (Device Description Document).";
            type string {
              length "0..256";
            }
          }
          leaf Server {
            config false;
            description
            "where '''UPnP''' is a literal string,
            '''udaversion''' is the version of the UPnP Device
            Architecture.";
            type string {
              length "0..256";
            }
          }
          leaf-list Host {
            config false;
            description
            "As such entries are added to or removed from the
            Host tables, the value of this parameter MUST be
            updated accordingly.";
            type string {
              length "0..256";
            }
          }
          leaf LastUpdate {
            config false;
            description
            "The date and time at which the last advertisement
            from this {{object}} was received.";
            type yang:date-and-time;
          }
        }
        list Service {
          key "USN";
          config false;
          description
          "UPnP embedded service table.  This table contains an
          entry for each UPnP embedded service that has been
          discovered via SSDP.";
          leaf Status {
            config false;
            description
            "The ability to list inactive UPnP embedded services
            is OPTIONAL. The length of time an inactive service
            remains listed in this table is a local matter to
            the CPE.";
            type enumeration {
              enum "LeaseActive" {
                description
                "Service is active and UPnP lease has not
                expired.";
              }
              enum "LeaseExpired" {
                description
                "Service is inactive because UPnP lease has
                expired.";
              }
              enum "ByebyeReceived" {
                description
                "Service is inactive because byebye message was
                received.";
              }
            }
          }
          leaf USN {
            config false;
            description
            ":
            ''uuid:device-UUID::urn:domain-name:service:serviceType:v''";
            type string {
              length "0..256";
            }
          }
          leaf LeaseTime {
            config false;
            description
            "The UPnP embedded service lease time in {{units}},
            extracted from the CACHE-CONTROL header.";
            type uint32;
          }
          leaf Location {
            config false;
            description
            "The value of the LOCATION header for this UPnP
            embedded service, which is the URL of the root
            device's DDD (Device Description Document).";
            type string {
              length "0..256";
            }
          }
          leaf Server {
            config false;
            description
            "where '''UPnP''' is a literal string,
            '''udaversion''' is the version of the UPnP Device
            Architecture.";
            type string {
              length "0..256";
            }
          }
          leaf-list Host {
            config false;
            description
            "As such entries are added to or removed from the
            Host tables, the value of this parameter MUST be
            updated accordingly.";
            type string {
              length "0..256";
            }
          }
          leaf LastUpdate {
            config false;
            description
            "The date and time at which the last advertisement
            from this {{object}} was received.";
            type yang:date-and-time;
          }
          leaf ParentDevice {
            config false;
            description
            "{{reference|the {{object|#.RootDevice}} or
            {{object|#.Device}} table entries that embeds this
            {{object}}}} This parameter is populated by
            extracting the \"device-UUID\" from the service's
            USN and matching the value against the root device
            or embedded device UUID value.";
            type string {
              length "0..256";
            }
          }
        }
      }
      container Description {
        description
        "This object contains information from the  Description
        Document discovered from the UPnP Devices and Services.";
        leaf DeviceDescriptionNumberOfEntries {
          config false;
          description
          "{{numentries}}";
          type uint32;
        }
        leaf DeviceInstanceNumberOfEntries {
          config false;
          description
          "{{numentries}}";
          type uint32;
        }
        leaf ServiceInstanceNumberOfEntries {
          config false;
          description
          "{{numentries}}";
          type uint32;
        }
        list DeviceDescription {
          key "URLBase";
          config false;
          description
          "In case the SSDP advertisement expires and the CPE
          deletes the related instances from the tables in
          UPnP.Discovery., the reference to such instances MUST
          be set to the empty string.";
          leaf URLBase {
            config false;
            description
            "Note: the URLBase element is not recommended by
            {{bibref|UPnP-DAv1}} and is not permitted by
            {{bibref|UPnP-DAv11}}, so the value of {{param}}
            will usually be the URL from which the device
            description was retrieved.";
            type string {
              length "0..256";
            }
          }
          leaf SpecVersion {
            config false;
            description
            "The UPnP Device Architecture version extracted from
            the specVersion element in the Device Description
            Document of the discovered root device.  The
            {{param}} is encoded as \"major revison.minor
            revision\". {{pattern}}";
            type string {
              length "0..256";
              pattern "\\d+\\.\\d+";
            }
          }
          leaf-list Host {
            config false;
            description
            "{{list}} {{reference|the Host table entries
            associated with the root device from which the
            device description was retrieved|ignore}}";
            type string {
              length "0..256";
            }
          }
        }
        list DeviceInstance {
          key "UDN";
          config false;
          description
          "This table contains the information from Device
          Description Document retrieved for a discovered UPnP
          root or embedded device.";
          leaf UDN {
            config false;
            description
            "This value is extracted from the UDN element in the
            Device Description Document with the leading uuid:
            removed.";
            type yang:uuid;
          }
          leaf ParentDevice {
            config false;
            description
            "{{reference|a {{object}} table entry (if this is an
            embedded device) or {{empty}} (if this is a root
            device)}}";
            type string {
              length "0..256";
            }
          }
          leaf DiscoveryDevice {
            config false;
            description
            "This {{param}} value can be {{empty}} because the
            referenced object has been deleted or the CPE was
            unable to retrieve the Description Document due to
            some out-of-band error.  The determination to
            delete this {{object}} or use {{empty}} is
            implementation specific.";
            type string {
              length "0..256";
            }
          }
          leaf DeviceType {
            config false;
            description
            "The value of the UPnP deviceType element in the
            Device Description Document for this {{object}}, or
            {{empty}} if this value is not provided by the
            device.";
            type string {
              length "0..256";
            }
          }
          leaf FriendlyName {
            config false;
            description
            "The value of the UPnP friendlyName element in the
            Device Description Document for this {{object}}, or
            {{empty}} if this value is not provided by the
            device.";
            type string {
              length "0..128";
            }
          }
          leaf-list DeviceCategory {
            config false;
            description
            "Note: {{param}} is different from
            {{param|DeviceType}} and is included here for the
            purpose of HTIP usage.";
            type string;
          }
          leaf Manufacturer {
            config false;
            description
            "The value of the UPnP manufacturer element in the
            Device Description Document for this {{object}}, or
            {{empty}} if this value is not provided by the
            device.";
            type string {
              length "0..128";
            }
          }
          leaf ManufacturerOUI {
            config false;
            description
            "Note: It is assumed that the
            ''htip:X_ManufacturerOUI'' element is used for HTIP
            (Home-network Topology Identifying Protocol)
            {{bibref|JJ-300.00}} and {{bibref|G.9973}}.";
            type string {
              length "0..6";
              pattern "^$|[0-9A-F]{6}";
            }
          }
          leaf ManufacturerURL {
            config false;
            description
            "The value of the UPnP manufacturerURL element in
            the Device Description Document for this
            {{object}}, or {{empty}} if this value is not
            provided by the device.";
            type string {
              length "0..256";
            }
          }
          leaf ModelDescription {
            config false;
            description
            "The value of the UPnP modelDescription element in
            the Device Description Document for this
            {{object}}, or {{empty}} if this value is not
            provided by the device.";
            type string {
              length "0..256";
            }
          }
          leaf ModelName {
            config false;
            description
            "The value of the UPnP modelName element in the
            Device Description Document for this {{object}}, or
            {{empty}} if this value is not provided by the
            device.";
            type string {
              length "0..64";
            }
          }
          leaf ModelNumber {
            config false;
            description
            "The value of the UPnP modelNumber element in the
            Device Description Document for this {{object}}, or
            {{empty}} if this value is not provided by the
            device.";
            type string {
              length "0..64";
            }
          }
          leaf ModelURL {
            config false;
            description
            "The value of the UPnP modelURL element in the
            Device Description Document for this {{object}}, or
            {{empty}} if this value is not provided by the
            device.";
            type string {
              length "0..256";
            }
          }
          leaf SerialNumber {
            config false;
            description
            "The value of the UPnP serialNumber element in the
            Device Description Document for this {{object}}, or
            {{empty}} if this value is not provided by the
            device.";
            type string {
              length "0..128";
            }
          }
          leaf UPC {
            config false;
            description
            "The value of the UPnP UPC element in the Device
            Description Document for this {{object}}, or
            {{empty}} if this value is not provided by the
            device.";
            type string {
              length "0..12";
            }
          }
          leaf PresentationURL {
            config false;
            description
            "If the presentationURL is not provided by the
            device then this value MUST be {{empty}}.";
            type string {
              length "0..256";
            }
          }
        }
        list ServiceInstance {
          key "ParentDevice ServiceId";
          config false;
          description
          "This table contains the information from Device
          Description Document retrieved for a discovered UPnP
          service.";
          leaf ParentDevice {
            config false;
            description
            "{{reference|a {{object|#.DeviceInstance}} table
            entry}}";
            type string {
              length "0..256";
            }
          }
          leaf ServiceId {
            config false;
            description
            "If the UPnP serviceId is not provided by the UPnP
            service, this {{object}} MUST be deleted.";
            type string {
              length "0..256";
            }
          }
          leaf ServiceDiscovery {
            config false;
            description
            "This {{param}} value can be {{empty}} because the
            referenced object has been deleted or the CPE was
            unable to retrieve the Description Document due to
            some out-of-band error.  The determination to
            delete this {{object}} or use {{empty}} is
            implementation specific.";
            type string {
              length "0..256";
            }
          }
          leaf ServiceType {
            config false;
            description
            "The value of the UPnP serviceType element in the
            Device Description Document for this {{object}}, or
            {{empty}} if this value is not provided by the
            service.";
            type string {
              length "0..256";
            }
          }
          leaf SCPDURL {
            config false;
            description
            "If the SCPDURL is not provided by the device then
            this value MUST be {{empty}}.";
            type string;
          }
          leaf ControlURL {
            config false;
            description
            "If the controlURL is not provided by the device
            then this value MUST be {{empty}}";
            type string;
          }
          leaf EventSubURL {
            config false;
            description
            "If the eventSubURL is not provided by the device
            then this value MUST be {{empty}}";
            type string;
          }
        }
      }
    }
    container DLNA {
      description
      "This object contains all DLNA related objects and
      parameters.";
      container Capabilities {
        description
        "DLNA capabilities.";
        leaf-list HNDDeviceClass {
          config false;
          description
          "{{list}} Indicates the supported DLNA Home Network
          Device Classes {{bibref|DLNA-NDIG|Table 4-1}}.";
          type string;
        }
        leaf-list DeviceCapability {
          config false;
          description
          "{{list}} Indicates the supported DLNA Device
          Capabilities {{bibref|DLNA-NDIG|Table 4-2}}.";
          type string;
        }
        leaf-list HIDDeviceClass {
          config false;
          description
          "{{list}} Indicates the supported DLNA Home
          Infrastructure Device Classes
          {{bibref|DLNA-NDIG|Table 4-4}}.";
          type string;
        }
        leaf-list ImageClassProfileID {
          config false;
          description
          "{{list}} Indicates the DLNA Image Class Profile IDs
          supported by this device, from Tables 5-2 and 5-3 of
          {{bibref|DLNA-NDIG}}.";
          type string;
        }
        leaf-list AudioClassProfileID {
          config false;
          description
          "{{list}} Indicates the DLNA Audio Class Profile IDs
          supported by this device, from Tables 5-4 through
          5-10 of {{bibref|DLNA-NDIG}}.";
          type string;
        }
        leaf-list AVClassProfileID {
          config false;
          description
          "{{list}} Indicates the DLNA AV Class Profile IDs
          supported by this device, from Tables 5-11 through
          5-15 of {{bibref|DLNA-NDIG}}.";
          type string;
        }
        leaf-list MediaCollectionProfileID {
          config false;
          description
          "{{list}} Indicates the DLNA Media Collection Profile
          IDs supported by this device {{bibref|DLNA-NDIG|Table
          5-16}}.";
          type string;
        }
        leaf-list PrinterClassProfileID {
          config false;
          description
          "{{list}} Indicates the DLNA Printer Class Profile IDs
          supported by this device {{bibref|DLNA-NDIG|Table
          5-17}}.";
          type string;
        }
      }
    }
    container SelfTestDiagnostics {
      description
      "This diagnostics test is vendor-specific and MAY include
      testing hardware, software, and/or firmware.";
      leaf DiagnosticsState {
        config true;
        description
        "While the test is in progress, setting this parameter
        to {{enum|Requested}} (and possibly modifying other
        writable parameters in this object) MUST result in the
        test being terminated and then restarted using the
        current values of the test parameters.";
        type enumeration {
          enum "None";
          enum "Requested";
          enum "Complete";
          enum "Error_Internal";
          enum "Error_Other";
        }
      }
      leaf Results {
        config false;
        description
        "Results of self-test (vendor specific).";
        type string {
          length "0..1024";
        }
      }
    }
    container Firewall {
      description
      "See {{bibref|TR-181i2a2|Appendix VIII}} for an example
      {{enum|Advanced|Config}} configuration.";
      leaf Enable {
        config true;
        description
        "Firewalls often implement additional Denial of Service
        and other vulnerability protections, such as those
        described in {{bibref|ICSA-Baseline}}. If a
        {{enum|Stateful|Type}} Firewall is enabled, then it is
        assumed that all implemented stateful protections are
        enabled, unless they are overridden by some other part
        of the data model.";
        type boolean;
      }
      leaf Config {
        config true;
        description
        "Vendors can extend the enumerated values with vendor
        specific extensions, in which case the rules outlined
        in {{bibref|TR-106a2|Section 3.3}} MUST be adhered to.";
        type enumeration {
          enum "High" {
            description
            "The firewall implements the \"Traffic Denied
            Inbound\" and \"Minimally Permit Common Services
            Outbound\" components of the ICSA residential
            certification's Required Services Security Policy
            {{bibref|ICSA-Residential}}.  If DoS and
            vulnerability protections are implemented
            {{bibref|ICSA-Baseline}}, these are enabled.";
          }
          enum "Low" {
            description
            "All Outbound traffic and pinhole-defined Inbound
            traffic is allowed.  If DoS and vulnerability
            protections are implemented
            {{bibref|ICSA-Baseline}}, these are enabled.";
          }
          enum "Off" {
            description
            "This value is DEPRECATED because it is the same as
            setting {{param|Enable}} to {{false}}.";
          }
          enum "Advanced" {
            description
            "Advanced firewall configuration applies, as
            specified by {{param|AdvancedLevel}}.";
          }
        }
      }
      leaf AdvancedLevel {
        config true;
        description
        "{{param}} only applies when {{param|Config}} is
        {{enum|Advanced|Config}}.";
        type string;
      }
      leaf Type {
        config false;
        description
        "A device that has a {{enum|Stateless}} Firewall depends
        on the NAT to provide protection against unsolicited
        downstream IPv4 traffic.  This is because, as noted
        above, a {{enum|Stateless}} Firewall has to be
        configured to accept all incoming downstream traffic.
        For IPv6 there is no NAT, so a {{enum|Stateless}}
        Firewall can not provide simple security protections
        against unsolicited downstream IPv6 traffic.";
        type enumeration {
          enum "Stateless" {
            description
            "The Firewall only implements stateless packet
            inspection.";
          }
          enum "Stateful" {
            description
            "The Firewall implements stateful packet inspection.";
          }
        }
      }
      leaf Version {
        config false;
        description
        "A string identifying the firewall settings version
        currently used in the CPE, or {{empty}} if the firewall
        settings are not associated with a version.";
        type string {
          length "0..16";
        }
      }
      leaf LastChange {
        config false;
        description
        "The time at which the firewall settings most recently
        changed.";
        type yang:date-and-time;
      }
      leaf LevelNumberOfEntries {
        config false;
        description
        "{{numentries}}";
        type uint32;
      }
      leaf ChainNumberOfEntries {
        config false;
        description
        "{{numentries}}";
        type uint32;
      }
      list Level {
        key "Name";
        unique "Alias";
        config true;
        description
        "Firewall Level table.  When an
        {{enum|Advanced|#.Config}} configuration is selected,
        {{param|#.AdvancedLevel}} selects the currently active
        entry in this table.  Each {{object}} table entry
        references the {{object|#.Chain}} that contains the
        rules for this level.";
        leaf Alias {
          config true;
          description
          "{{datatype|expand}}";
          type Alias;
        }
        leaf Name {
          config true;
          description
          "Human-readable name associated with this {{object}}
          entry.";
          type string {
            length "0..64";
          }
        }
        leaf Description {
          config true;
          description
          "Human-readable description associated with this
          {{object}} entry.";
          type string {
            length "0..256";
          }
        }
        leaf Order {
          config true;
          description
          "The value of {{param}} on creation of a {{object}}
          table entry MUST be one greater than the largest
          current value.";
          type uint32 {
            range "1..max";
          }
        }
        leaf Chain {
          config false;
          description
          "On creation of a new {{object}} entry, the device
          will automatically create a new {{object|#.Chain}}
          table entry that this {{param}} parameter will
          reference.";
          type string;
        }
        leaf PortMappingEnabled {
          config true;
          description
          "This parameter affects all the interfaces on which
          NAT is enabled.  It operationally enables or disables
          port mapping functionality and therefore does not
          affect the individual
          {{param|##.NAT.PortMapping.{i}.Enable}} settings.
          Note that the current NAT status and NAT port mapping
          status are indicated by the
          {{param|##.NAT.InterfaceSetting.{i}.Status}}
          parameter.";
          type boolean;
          default "true";
        }
        leaf DefaultPolicy {
          config true;
          description
          "Default action for packets not matching any of the
          level rules.  {{enum}}";
          type enumeration {
            enum "Drop" {
              description
              "The firewall discards packets matching this rule.";
            }
            enum "Accept" {
              description
              "The firewall forwards packets matching this rule.";
            }
            enum "Reject" {
              description
              "The firewall discards packets matching this rule,
              and sends an ICMP message to the originating
              host.";
            }
          }
          default "Drop";
        }
        leaf DefaultLogPolicy {
          config true;
          description
          "Enable or disable logging, in a
          {{object|##.DeviceInfo.VendorLogFile}}, of packets
          not matching any of the level rules.";
          type boolean;
          default "false";
        }
      }
      list Chain {
        key "Name";
        unique "Alias";
        config true;
        description
        "A given Firewall Chain's rules are all created by the
        same entity, as indicated by the {{param|Creator}}
        parameter.";
        leaf Enable {
          config true;
          description
          "Enables or disables this {{object}} entry.";
          type boolean;
          default "false";
        }
        leaf Alias {
          config true;
          description
          "{{datatype|expand}}";
          type Alias;
        }
        leaf Name {
          config true;
          description
          "Human-readable name associated with this {{object}}
          entry.";
          type string {
            length "0..64";
          }
        }
        leaf Creator {
          config false;
          description
          "Note that this is the entity that originally created
          the {{object}} entry.  The value of this parameter
          does not change if the {{object}} entry or one of its
          rules is subsequently changed by another entity.";
          type enumeration {
            enum "Defaults" {
              description
              "The {{object}} entry is present in the factory
              default configuration.";
            }
            enum "PortMapping" {
              description
              "The {{object}} entry was created as a side-effect
              of a {{bibref|UPnP-IGD:1}} or {{bibref|TR-064}}
              port mapping.";
            }
            enum "WANIPv6FirewallControl" {
              description
              "The {{object}} entry was created by
              {{bibref|UPnP-IGD:2}} WANIPv6FirewallControl.";
            }
            enum "ACS" {
              description
              "The {{object}} entry was created by the Auto
              Configuration Server.";
            }
            enum "UserInterface" {
              description
              "The {{object}} entry was created by device user
              interface or command line interface.";
            }
            enum "Other" {
              description
              "The {{object}} entry was created by another
              entity.";
            }
          }
          default "ACS";
        }
        leaf RuleNumberOfEntries {
          config false;
          description
          "{{numentries}}";
          type uint32;
        }
        list Rule {
          key "Alias";
          config true;
          description
          "For enabled table entries, if
          {{param|SourceInterface}} is not a valid reference
          and {{param|SourceAllInterfaces}} is {{false}}, or if
          {{param|DestInterface}} is not a valid reference and
          {{param|DestAllInterfaces}} is {{false}}, then the
          table entry is inoperable and the CPE MUST set
          {{param|Status}} to
          {{enum|Error_Misconfigured|Status}}.";
          leaf Enable {
            config true;
            description
            "Enables or disables this {{object}} entry.";
            type boolean;
            default "false";
          }
          leaf Status {
            config false;
            description
            "The {{enum|Error}} value MAY be used by the CPE to
            indicate a locally defined error condition.";
            type enumeration {
              enum "Disabled";
              enum "Enabled";
              enum "Error_Misconfigured";
              enum "Error";
            }
            default "Disabled";
          }
          leaf Order {
            config true;
            description
            "The value of {{param}} on creation of a {{object}}
            table entry MUST be one greater than the largest
            current value (initially assigned the lowest
            precedence).";
            type uint32 {
              range "1..max";
            }
          }
          leaf Alias {
            config true;
            description
            "{{datatype|expand}}";
            type Alias;
          }
          leaf Description {
            config true;
            description
            "Human-readable description associated with this
            {{object}} entry.";
            type string {
              length "0..256";
            }
          }
          leaf Target {
            config true;
            description
            "This parameter can only be modified if the
            {{object}} is ''Static'' (as explained in the
            object description).";
            type enumeration {
              enum "Drop" {
                description
                "The firewall discards packets matching this
                rule.";
              }
              enum "Accept" {
                description
                "The firewall forwards packets matching this
                rule.";
              }
              enum "Reject" {
                description
                "The firewall discards packets matching this
                rule, and sends an ICMP message to the
                originating host.";
              }
              enum "Return" {
                description
                "The firewall doesn't consider the remaining
                rules (if any) in the current chain.";
              }
              enum "TargetChain" {
                description
                "The rules in the chain referenced by the
                {{param|TargetChain}} parameter are matched.";
              }
            }
            default "Drop";
          }
          leaf TargetChain {
            config true;
            description
            "This parameter can only be modified if the
            {{object}} is ''Static'' (as explained in the
            object description).";
            type string;
          }
          leaf Log {
            config true;
            description
            "If the {{object}} is not ''Static'' (as explained
            in the object description), whether changes to this
            parameter persist across re-boot is a local matter
            to the CPE.";
            type boolean;
            default "false";
          }
          leaf CreationDate {
            config false;
            description
            "Date and time when this {{object}} entry was
            created.";
            type yang:date-and-time;
          }
          leaf ExpiryDate {
            config true;
            description
            "This parameter can only be modified if the
            {{object}} is ''Static'' (as explained in the
            object description).";
            type yang:date-and-time;
            default "9999-12-31T23:59:59Z";
          }
          leaf SourceInterface {
            config true;
            description
            "This parameter can only be modified if the
            {{object}} is ''Static'' (as explained in the
            object description).";
            type string {
              length "0..256";
            }
          }
          leaf SourceInterfaceExclude {
            config true;
            description
            "This parameter can only be modified if the
            {{object}} is ''Static'' (as explained in the
            object description).";
            type boolean;
            default "false";
          }
          leaf SourceAllInterfaces {
            config true;
            description
            "This parameter can only be modified if the
            {{object}} is ''Static'' (as explained in the
            object description).";
            type boolean;
            default "false";
          }
          leaf DestInterface {
            config true;
            description
            "This parameter can only be modified if the
            {{object}} is ''Static'' (as explained in the
            object description).";
            type string {
              length "0..256";
            }
          }
          leaf DestInterfaceExclude {
            config true;
            description
            "This parameter can only be modified if the
            {{object}} is ''Static'' (as explained in the
            object description).";
            type boolean;
            default "false";
          }
          leaf DestAllInterfaces {
            config true;
            description
            "This parameter can only be modified if the
            {{object}} is ''Static'' (as explained in the
            object description).";
            type boolean;
            default "false";
          }
          leaf IPVersion {
            config true;
            description
            "This parameter can only be modified if the
            {{object}} is ''Static'' (as explained in the
            object description).";
            type int32 {
              range "-1..15";
            }
            default "-1";
          }
          leaf DestIP {
            config true;
            description
            "This parameter can only be modified if the
            {{object}} is ''Static'' (as explained in the
            object description).";
            type inet:ip-address;
          }
          leaf DestMask {
            config true;
            description
            "Destination IP address mask, represented as an IP
            routing prefix using CIDR notation [RFC4632]. The
            IP address part MUST be {{empty}} (and, if
            specified, MUST be ignored).";
            type inet:ip-prefix;
          }
          leaf DestIPExclude {
            config true;
            description
            "This parameter can only be modified if the
            {{object}} is ''Static'' (as explained in the
            object description).";
            type boolean;
            default "false";
          }
          leaf SourceIP {
            config true;
            description
            "This parameter can only be modified if the
            {{object}} is ''Static'' (as explained in the
            object description).";
            type inet:ip-address;
          }
          leaf SourceMask {
            config true;
            description
            "Source IP address mask, represented as an IP
            routing prefix using CIDR notation [RFC4632]. The
            IP address part MUST be {{empty}} (and, if
            specified, MUST be ignored).";
            type inet:ip-prefix;
          }
          leaf SourceIPExclude {
            config true;
            description
            "This parameter can only be modified if the
            {{object}} is ''Static'' (as explained in the
            object description).";
            type boolean;
            default "false";
          }
          leaf Protocol {
            config true;
            description
            "This parameter can only be modified if the
            {{object}} is ''Static'' (as explained in the
            object description).";
            type int32 {
              range "-1..255";
            }
            default "-1";
          }
          leaf ProtocolExclude {
            config true;
            description
            "This parameter can only be modified if the
            {{object}} is ''Static'' (as explained in the
            object description).";
            type boolean;
            default "false";
          }
          leaf DestPort {
            config true;
            description
            "This parameter can only be modified if the
            {{object}} is ''Static'' (as explained in the
            object description).";
            type int32 {
              range "-1..65535";
            }
            default "-1";
          }
          leaf DestPortRangeMax {
            config true;
            description
            "This parameter can only be modified if the
            {{object}} is ''Static'' (as explained in the
            object description).";
            type int32 {
              range "-1..65535";
            }
            default "-1";
          }
          leaf DestPortExclude {
            config true;
            description
            "This parameter can only be modified if the
            {{object}} is ''Static'' (as explained in the
            object description).";
            type boolean;
            default "false";
          }
          leaf SourcePort {
            config true;
            description
            "This parameter can only be modified if the
            {{object}} is ''Static'' (as explained in the
            object description).";
            type int32 {
              range "-1..65535";
            }
            default "-1";
          }
          leaf SourcePortRangeMax {
            config true;
            description
            "This parameter can only be modified if the
            {{object}} is ''Static'' (as explained in the
            object description).";
            type int32 {
              range "-1..65535";
            }
            default "-1";
          }
          leaf SourcePortExclude {
            config true;
            description
            "This parameter can only be modified if the
            {{object}} is ''Static'' (as explained in the
            object description).";
            type boolean;
            default "false";
          }
          leaf DSCP {
            config true;
            description
            "This parameter can only be modified if the
            {{object}} is ''Static'' (as explained in the
            object description).";
            type int32 {
              range "-1..63";
            }
            default "-1";
          }
          leaf DSCPExclude {
            config true;
            description
            "This parameter can only be modified if the
            {{object}} is ''Static'' (as explained in the
            object description).";
            type boolean;
            default "false";
          }
        }
      }
    }
    container PeriodicStatistics {
      description
      "This object provides a single set of global settings that
      affect the entire device unless overridden locally.";
      leaf MinSampleInterval {
        config false;
        description
        "A value of 0 indicates no specific minimum sample
        interval.";
        type uint32;
      }
      leaf MaxReportSamples {
        config false;
        description
        "A value of 0 indicates no specific maximum number of
        samples.";
        type uint32;
      }
      leaf SampleSetNumberOfEntries {
        config false;
        description
        "{{numentries}}";
        type uint32;
      }
      list SampleSet {
        key "Name";
        unique "Alias";
        config true;
        description
        "Periodic statistics sample set table.  Each sample set
        has its own sample interval etc.";
        leaf Alias {
          config true;
          description
          "{{datatype|expand}}";
          type Alias;
        }
        leaf Enable {
          config true;
          description
          "When collection of periodic statistics is enabled,
          any stored samples are discarded, and the first
          sample interval begins immediately.";
          type boolean;
          default "false";
        }
        leaf Status {
          config false;
          description
          "The transition from {{enum|Enabled}} to
          {{enum|Trigger}} to {{enum|Enabled}} MUST be
          instantaneous and so will result in only a single
          value change for notification purposes.";
          type enumeration {
            enum "Disabled" {
              description
              "Collection is disabled.";
            }
            enum "Enabled" {
              description
              "Collection is enabled.";
            }
            enum "Trigger" {
              description
              "Collection is enabled and the ACS SHOULD now
              fetch the collected data.";
            }
          }
          default "Disabled";
        }
        leaf Name {
          config true;
          description
          "The name of this sample set, which uniquely
          distinguishes each sample set.";
          type string {
            length "0..128";
          }
        }
        leaf SampleInterval {
          config true;
          description
          "For example, if {{param|ReportSamples}} is 24 and
          {{param}} is 3600 (an hour), the CPE can store up to
          a day's worth of samples for each statistic.";
          type uint32 {
            range "1..max";
          }
          default "3600";
        }
        leaf ReportSamples {
          config true;
          description
          "For example, if {{param}} is 24 and
          {{param|SampleInterval}} is 3600 (an hour), the CPE
          can store up to a day's worth of samples for each
          statistic.";
          type uint32 {
            range "1..max";
          }
          default "24";
        }
        leaf TimeReference {
          config true;
          description
          "Note that, if {{param}} is set to a time other than
          the Unknown Time, the first sample interval (which
          has to begin immediately) will almost certainly be
          shorter than {{param|SampleInterval}}).  This is why
          {{param}} is defined in terms of when sample
          intervals complete rather than start.";
          type yang:date-and-time;
          default "0001-01-01T00:00:00Z";
        }
        leaf FetchSamples {
          config true;
          description
          "To disable this trigger mechanism and still collect
          sampled statistics, {{param}} can be set to either 0
          or a value greater than {{param|ReportSamples}}.";
          type uint32;
          default "0";
        }
        leaf ForceSample {
          config true;
          description
          "At the end of each sample interval, if {{param}} was
          set to {{true}} during the sample interval then the
          new values that were added as described above, and
          the {{param|ReportEndTime}} and all
          {{param|SampleSeconds}} parameters, will be updated
          accordingly.  In other words, the partial sample data
          that was created when {{param}} was set to {{true}}
          will be updated one last time at the end of the
          sample interval.";
          type boolean;
          default "false";
        }
        leaf ReportStartTime {
          config false;
          description
          "The absolute time at which the sample interval for
          the first stored sample (for each statistic) started.";
          type yang:date-and-time;
        }
        leaf ReportEndTime {
          config false;
          description
          "If {{param|ForceSample}} has been used to force
          statistics for the current sample to be calculated
          and updated in the data model, then {{param}} MUST be
          updated to reflect the actual time over which stored
          data was collected.";
          type yang:date-and-time;
        }
        leaf-list SampleSeconds {
          config false;
          description
          ": {{param|ForceSample}} has been used to force
          statistics for the current sample to be calculated
          and updated in the data model.";
          type uint32;
        }
        leaf ParameterNumberOfEntries {
          config false;
          description
          "{{numentries}}";
          type uint32;
          default "0";
        }
        list Parameter {
          key "Reference";
          unique "Alias";
          config true;
          description
          "Note that the comma-separated lists in this object
          (SampleSeconds, SuspectData and Values) only ever
          change (a) when first enabled, (b) when ForceSample
          is set to true (a \"sneak preview\" of the current
          sample), or (c) at the end of the sample interval.";
          leaf Alias {
            config true;
            description
            "{{datatype|expand}}";
            type Alias;
          }
          leaf Enable {
            config true;
            description
            "Enables or disables this object instance.";
            type boolean;
            default "false";
          }
          leaf Reference {
            config true;
            description
            "{{reference}} This is the parameter being monitored
            by the Periodic Statistics mechanism.";
            type string {
              length "0..256";
            }
          }
          leaf SampleMode {
            config true;
            description
            "Parameters of non-numeric types can only support
            {{enum|Current}}.  The value of the {{param}} MUST
            be ignored for such parameters.";
            type enumeration {
              enum "Current" {
                description
                "Sampled value is current value";
              }
              enum "Change" {
                description
                "Sampled value is change in value since start of
                sample interval";
              }
            }
            default "Current";
          }
          leaf CalculationMode {
            config true;
            description
            "{{param|SampleMode}} MUST be applied before
            {{param}}, i.e.  the inputs to the calculation will
            have already accounted for {{param|SampleMode}}.";
            type enumeration {
              enum "Latest" {
                description
                "Statistic is sampled value at end of sample
                interval";
              }
              enum "Minimum" {
                description
                "Statistic is minimum sampled value during
                sample interval";
              }
              enum "Maximum" {
                description
                "Statistic is maximum sampled value during
                sample interval";
              }
              enum "Average" {
                description
                "Statistic is average (mean) sampled value
                during sample interval";
              }
            }
            default "Latest";
          }
          leaf LowThreshold {
            config true;
            description
            "Parameters of non-numeric types cannot support the
            threshold/failure mechanism.  The value of this
            parameter MUST be ignored for such parameters.";
            type int32;
            default "0";
          }
          leaf HighThreshold {
            config true;
            description
            "Parameters of non-numeric types cannot support the
            threshold/failure mechanism.  The value of this
            parameter MUST be ignored for such parameters.";
            type int32;
            default "0";
          }
          leaf-list SampleSeconds {
            config false;
            description
            ": The parameter doesn't exist, or was created or
            deleted during a sample interval.";
            type uint32;
          }
          leaf-list SuspectData {
            config false;
            description
            "For example, if the parameter value were to be
            reset during the sample interval then it would be
            appropriate to set {{param}} to 1.";
            type uint32 {
              range "min..1";
            }
          }
          leaf-list Values {
            config false;
            description
            "If the {{param|SampleMode}} parameter is not
            present, or is inappropriate for the referenced
            parameter, the statistics values MUST be collected
            in Current mode.";
            type string;
          }
          leaf Failures {
            config false;
            description
            "Parameters of non-numeric types cannot support the
            threshold/failure mechanism.  The value of this
            parameter MUST be ignored for such parameters.";
            type uint32;
            default "0";
          }
        }
      }
    }
    container FaultMgmt {
      description
      "This object contains parameters relating to Fault/Alarm
      Management.";
      leaf SupportedAlarmNumberOfEntries {
        config false;
        description
        "{{numentries}}";
        type uint32;
      }
      leaf MaxCurrentAlarmEntries {
        config false;
        description
        "The maximum number of entries allowed in the
        {{object|.FaultMgmt.CurrentAlarm.{i}.}} table.";
        type uint32;
      }
      leaf CurrentAlarmNumberOfEntries {
        config false;
        description
        "{{numentries}}";
        type uint32;
      }
      leaf HistoryEventNumberOfEntries {
        config false;
        description
        "{{numentries}}";
        type uint32;
      }
      leaf ExpeditedEventNumberOfEntries {
        config false;
        description
        "{{numentries}}";
        type uint32;
      }
      leaf QueuedEventNumberOfEntries {
        config false;
        description
        "{{numentries}}";
        type uint32;
      }
      list SupportedAlarm {
        key "EventType ProbableCause SpecificProblem PerceivedSeverity";
        config true;
        description
        "The instance numbers for this table SHOULD be
        maintained across firmware upgrades of the device.";
        leaf EventType {
          config true;
          description
          "Indicates the type of event.";
          type string {
            length "0..64";
          }
        }
        leaf ProbableCause {
          config true;
          description
          "Qualifies the alarm and provides further information
          than {{param|EventType}}.";
          type string {
            length "0..64";
          }
        }
        leaf SpecificProblem {
          config true;
          description
          "The string can be set to \"*\" to indicate the
          default case if only a subset of {{param}} are to be
          contained within the table.";
          type string {
            length "0..128";
          }
        }
        leaf PerceivedSeverity {
          config true;
          description
          "The string can be set to \"*\" to indicate the
          default case if only a subset of {{param}} are to be
          contained within the table.";
          type enumeration {
            enum "<empty>" {
              description
              "{{empty}}";
            }
            enum "*";
            enum "Cleared";
            enum "Critical";
            enum "Major";
            enum "Minor";
            enum "Warning";
            enum "Indeterminate";
          }
        }
        leaf ReportingMechanism {
          config true;
          description
          "Indicates the reporting mechanism setting of the
          alarm.  {{enum}}";
          type enumeration {
            enum "0 Expedited" {
              description
              "The device inserts the alarm into the
              {{object|.FaultMgmt.ExpeditedEvent.{i}.}} table
              and the {{object|.FaultMgmt.ExpeditedEvent.{i}.}}
              table.";
            }
            enum "1 Queued" {
              description
              "The device inserts the alarm into the
              {{object|.FaultMgmt.QueuedEvent.{i}.}} table and
              the {{object|.FaultMgmt.QueuedEvent.{i}.}} table.";
            }
            enum "2 Logged" {
              description
              "The device inserts the alarm into the
              {{object|.FaultMgmt.HistoryEvent.{i}.}} table.";
            }
            enum "3 Disabled" {
              description
              "The device ignores the alarm.";
            }
          }
        }
      }
      list CurrentAlarm {
        key "AlarmIdentifier";
        unique "EventType ProbableCause SpecificProblem";
        config false;
        description
        "When a new alarm replaces an existing alarm, then all
        parameter values for that instance are considered as
        changed for the purposes of value change notifications
        to the ACS (even if their new values are identical to
        those of the prior alarm).";
        leaf AlarmIdentifier {
          config false;
          description
          "Identifies one Alarm Entry in the Alarm List.  This
          value MUST be uniquely allocated by the device to the
          alarm instance during the lifetime of the individual
          alarm.";
          type string {
            length "0..64";
          }
        }
        leaf AlarmRaisedTime {
          config false;
          description
          "Indicates the date and time when the alarm was first
          raised by the device.";
          type yang:date-and-time;
        }
        leaf AlarmChangedTime {
          config false;
          description
          "Indicates the date and time when the alarm was last
          changed by the device.";
          type yang:date-and-time;
        }
        leaf ManagedObjectInstance {
          config false;
          description
          "Specifies the instance of the Informational Object
          Class in which the alarm occurred by carrying the
          Distinguished Name (DN) of this object instance.  The
          format of the DN is specific to the application that
          is using this {{object}}.";
          type string {
            length "0..512";
          }
        }
        leaf EventType {
          config false;
          description
          "Indicates the type of event.";
          type string {
            length "0..64";
          }
        }
        leaf ProbableCause {
          config false;
          description
          "Qualifies the alarm and provides further information
          than {{param|EventType}}.";
          type string {
            length "0..64";
          }
        }
        leaf SpecificProblem {
          config false;
          description
          "This is vendor defined and will be {{empty}} if the
          device doesn't support inclusion of this information.";
          type string {
            length "0..128";
          }
        }
        leaf PerceivedSeverity {
          config false;
          description
          "Indicates the relative level of urgency for operator
          attention, see {{bibref|ITU-X.733}}. {{enum}}";
          type enumeration {
            enum "Critical";
            enum "Major";
            enum "Minor";
            enum "Warning";
            enum "Indeterminate";
          }
        }
        leaf AdditionalText {
          config false;
          description
          "This will be {{empty}} if the device doesn't support
          inclusion of this information.";
          type string {
            length "0..256";
          }
        }
        leaf AdditionalInformation {
          config false;
          description
          "This contains additional information about the alarm
          and is vendor defined.";
          type string {
            length "0..256";
          }
        }
      }
      list HistoryEvent {
        key "EventTime AlarmIdentifier";
        config false;
        description
        "If maximum instance number
        {{param|.FaultMgmt.HistoryEventNumberOfEntries}} is
        reached, the next event overrides the object with
        instance number 1.  Subsequent entries override objects
        at sequentially increasing instance numbers.  This
        logic provides for automatic \"rolling\" of records.";
        leaf EventTime {
          config false;
          description
          "Indicates the date and time when the alarm event
          occurs.";
          type yang:date-and-time;
        }
        leaf AlarmIdentifier {
          config false;
          description
          "Identifies one Alarm Entry in the Alarm List.  This
          value MUST be uniquely allocated by the device to the
          alarm instance during the lifetime of the individual
          alarm.";
          type string {
            length "0..64";
          }
        }
        leaf NotificationType {
          config false;
          description
          "Indicates the reason for the specific alarm
          notification event.  {{enum}}";
          type enumeration {
            enum "NewAlarm";
            enum "ChangedAlarm";
            enum "ClearedAlarm";
          }
        }
        leaf ManagedObjectInstance {
          config false;
          description
          "Specifies the instance of the Informational Object
          Class in which the alarm occurred by carrying the
          Distinguished Name (DN) of this object instance.  The
          format of the DN is specific to the application that
          is using this {{object}}.";
          type string {
            length "0..512";
          }
        }
        leaf EventType {
          config false;
          description
          "Indicates the type of event.";
          type string {
            length "0..64";
          }
        }
        leaf ProbableCause {
          config false;
          description
          "Qualifies the alarm and provides further information
          than {{param|EventType}}.";
          type string {
            length "0..64";
          }
        }
        leaf SpecificProblem {
          config false;
          description
          "This is vendor defined and will be {{empty}} if the
          device doesn't support inclusion of this information.";
          type string {
            length "0..128";
          }
        }
        leaf PerceivedSeverity {
          config false;
          description
          "Indicates the relative level of urgency for operator
          attention, see {{bibref|ITU-X.733}}. {{enum}}";
          type enumeration {
            enum "Cleared";
            enum "Critical";
            enum "Major";
            enum "Minor";
            enum "Warning";
            enum "Indeterminate";
          }
        }
        leaf AdditionalText {
          config false;
          description
          "This will be {{empty}} if the device doesn't support
          inclusion of this information.";
          type string {
            length "0..256";
          }
        }
        leaf AdditionalInformation {
          config false;
          description
          "This contains additional information about the alarm
          and is vendor defined.";
          type string {
            length "0..256";
          }
        }
      }
      list ExpeditedEvent {
        key "AlarmIdentifier";
        config false;
        description
        "When a new alarm replaces an existing alarm, then all
        parameter values for that instance are considered as
        changed for the purposes of value change notifications
        to the ACS (even if their new values are identical to
        those of the prior alarm).";
        leaf EventTime {
          config false;
          description
          "For an unpopulated entry, the value is the Unknown
          Time as defined in {{bibref|TR-106a4}}.";
          type yang:date-and-time;
        }
        leaf AlarmIdentifier {
          config false;
          description
          "For an unpopulated entry, the value is {{empty}}.";
          type string {
            length "0..64";
          }
        }
        leaf NotificationType {
          config false;
          description
          "Indicates the reason for the specific alarm
          notification event.  {{enum}}";
          type enumeration {
            enum "NewAlarm";
            enum "ChangedAlarm";
            enum "ClearedAlarm";
          }
        }
        leaf ManagedObjectInstance {
          config false;
          description
          "Specifies the instance of the Informational Object
          Class in which the alarm occurred by carrying the
          Distinguished Name (DN) of this object instance.  The
          format of the DN is specific to the application that
          is using this {{object}}.";
          type string {
            length "0..512";
          }
        }
        leaf EventType {
          config false;
          description
          "Indicates the type of event.";
          type string {
            length "0..64";
          }
        }
        leaf ProbableCause {
          config false;
          description
          "Qualifies the alarm and provides further information
          than {{param|EventType}}.";
          type string {
            length "0..64";
          }
        }
        leaf SpecificProblem {
          config false;
          description
          "This is vendor defined and will be {{empty}} if the
          device doesn't support inclusion of this information.";
          type string {
            length "0..128";
          }
        }
        leaf PerceivedSeverity {
          config false;
          description
          "Indicates the relative level of urgency for operator
          attention, see {{bibref|ITU-X.733}}. {{enum}}";
          type enumeration {
            enum "Cleared";
            enum "Critical";
            enum "Major";
            enum "Minor";
            enum "Warning";
            enum "Indeterminate";
          }
        }
        leaf AdditionalText {
          config false;
          description
          "This will be {{empty}} if the device doesn't support
          inclusion of this information.";
          type string {
            length "0..256";
          }
        }
        leaf AdditionalInformation {
          config false;
          description
          "This contains additional information about the alarm
          and is vendor defined.";
          type string {
            length "0..256";
          }
        }
      }
      list QueuedEvent {
        key "AlarmIdentifier";
        config false;
        description
        "When a new alarm replaces an existing alarm, then all
        parameter values for that instance are considered as
        changed for the purposes of value change notifications
        to the ACS (even if their new values are identical to
        those of the prior alarm).";
        leaf EventTime {
          config false;
          description
          "For an unpopulated entry, the value is the Unknown
          Time as defined in {{bibref|TR-106a4}}.";
          type yang:date-and-time;
        }
        leaf AlarmIdentifier {
          config false;
          description
          "For an unpopulated entry, the value is {{empty}}.";
          type string {
            length "0..64";
          }
        }
        leaf NotificationType {
          config false;
          description
          "Indicates the reason for the specific alarm
          notification event.  {{enum}}";
          type enumeration {
            enum "NewAlarm";
            enum "ChangedAlarm";
            enum "ClearedAlarm";
          }
        }
        leaf ManagedObjectInstance {
          config false;
          description
          "Specifies the instance of the Informational Object
          Class in which the alarm occurred by carrying the
          Distinguished Name (DN) of this object instance.  The
          format of the DN is specific to the application that
          is using this {{object}}.";
          type string {
            length "0..512";
          }
        }
        leaf EventType {
          config false;
          description
          "Indicates the type of event.";
          type string {
            length "0..64";
          }
        }
        leaf ProbableCause {
          config false;
          description
          "Qualifies the alarm and provides further information
          than {{param|EventType}}.";
          type string {
            length "0..64";
          }
        }
        leaf SpecificProblem {
          config false;
          description
          "This is vendor defined and will be {{empty}} if the
          device doesn't support inclusion of this information.";
          type string {
            length "0..128";
          }
        }
        leaf PerceivedSeverity {
          config false;
          description
          "Indicates the relative level of urgency for operator
          attention, see {{bibref|ITU-X.733}}. {{enum}}";
          type enumeration {
            enum "Cleared";
            enum "Critical";
            enum "Major";
            enum "Minor";
            enum "Warning";
            enum "Indeterminate";
          }
        }
        leaf AdditionalText {
          config false;
          description
          "This will be {{empty}} if the device doesn't support
          inclusion of this information.";
          type string {
            length "0..256";
          }
        }
        leaf AdditionalInformation {
          config false;
          description
          "This contains additional information about the alarm
          and is vendor defined.";
          type string {
            length "0..256";
          }
        }
      }
    }
    container Security {
      description
      "This object contains general information related to
      managing security features on the device.";
      leaf CertificateNumberOfEntries {
        config false;
        description
        "{{numentries}}";
        type uint32;
      }
      list Certificate {
        key "SerialNumber Issuer";
        config true;
        description
        "This table provides information about all types of
        public key-based credentials, such as X.509
        certificates, see {{bibref|RFC5280}}.";
        leaf Enable {
          config true;
          description
          "Enables or disables this certificate.";
          type boolean;
        }
        leaf LastModif {
          config false;
          description
          "The last modification time of this certificate.";
          type yang:date-and-time;
        }
        leaf SerialNumber {
          config true;
          description
          "The Serial Number field in an X.509 certificate, see
          {{bibref|RFC5280}}.";
          type string {
            length "0..64";
          }
        }
        leaf Issuer {
          config true;
          description
          "The Issuer field in an X.509 certificate, see
          {{bibref|RFC5280}}; i.e.  the Distinguished Name (DN)
          of the entity who has signed the certificate.";
          type string {
            length "0..256";
          }
        }
        leaf NotBefore {
          config false;
          description
          "The beginning of the certificate validity period;
          i.e.  the Not Before field in an X.509 certificate,
          see {{bibref|RFC5280}}.";
          type yang:date-and-time;
        }
        leaf NotAfter {
          config false;
          description
          "The end of the certificate validity period; i.e., the
          Not After field in an X.509 certificate, see
          {{bibref|RFC5280}}.";
          type yang:date-and-time;
        }
        leaf Subject {
          config false;
          description
          "The Distinguished Name (DN) of the entity associated
          with the Public Key; i.e., the Subject field in an
          X.509 certificate, see {{bibref|RFC5280}}.";
          type string {
            length "0..256";
          }
        }
        leaf-list SubjectAlt {
          config false;
          description
          "The Subject Alternative Names extension field in an
          X.509 certificate, see {{bibref|RFC5280}}.";
          type string;
        }
        leaf SignatureAlgorithm {
          config false;
          description
          "The algorithm used in signing the certificate; i.e.
          the Signature Algorithm field in an X.509
          certificate, see {{bibref|RFC5280}}.";
          type string {
            length "0..256";
          }
        }
      }
    }
    container FAP {
      description
      "This object is the container for all Femto related
      component objects, to prevent pollution of the so-called
      global namespace of the BBF with FAP specific objects.";
      container GPS {
        description
        "This object contains the parameters relating to the GPS
        scan.";
        leaf ScanOnBoot {
          config true;
          description
          "Enables or disables GPS scans during the device start
          up.";
          type boolean;
          default "true";
        }
        leaf ScanPeriodically {
          config true;
          description
          "Enables or disables periodic GPS scans.";
          type boolean;
          default "false";
        }
        leaf PeriodicInterval {
          config true;
          description
          "When {{param|ScanPeriodically}} is {{true}}, this
          value indicates the interval in {{units}} which GPS
          scan is performed.";
          type uint32;
        }
        leaf PeriodicTime {
          config true;
          description
          "If absolute time is not available to the CPE, its
          periodic GPS scan behavior MUST be the same as if
          {{param}} parameter was set to the Unknown Time
          value.";
          type yang:date-and-time;
        }
        leaf ContinuousGPS {
          config true;
          description
          "Whether or not the device SHOULD maintain a
          continuous GPS lock (e.g.  as a frequency stability
          source).";
          type boolean;
        }
        leaf ScanTimeout {
          config true;
          description
          "Specifies the time-out value in {{units}} since the
          scan started after which the scan will time out.  A
          timed out scan is to be reported as
          {{enum|Error_TIMEOUT|ScanStatus}} with
          {{param|ErrorDetails}} indicating \"Timed out\"";
          type uint32;
        }
        leaf ScanStatus {
          config false;
          description
          "Indicates the current status of this scan.";
          type enumeration {
            enum "Indeterminate" {
              description
              "The scan has not been executed and there are no
              valid scan results available";
            }
            enum "InProgress";
            enum "Success";
            enum "Error";
            enum "Error_TIMEOUT";
          }
        }
        leaf ErrorDetails {
          config false;
          description
          "Provides more detail when the {{param|ScanStatus}} is
          either {{enum|Error|ScanStatus}} or
          {{enum|Error_TIMEOUT|ScanStatus}}.";
          type string {
            length "0..256";
          }
        }
        leaf LastScanTime {
          config false;
          description
          "The date and time when the last GPS scan completed.";
          type yang:date-and-time;
        }
        leaf LastSuccessfulScanTime {
          config false;
          description
          "The values for {{param|LockedLatitude}},
          {{param|LockedLongitude}} and
          {{param|NumberOfSatellites}} correspond to this time.
          If a scan has never succeeded before, the value will
          be the Unknown Time value, as defined in
          {{bibref|TR-106a4|Section 3.2}}.";
          type yang:date-and-time;
        }
        leaf LockedLatitude {
          config false;
          description
          "This value is retained across reboots and is only
          reset after another scan completes successfully or
          {{param|GPSReset}} is set to {{true}}. If a scan has
          never succeeded before, the value 0 is reported.";
          type int32 {
            range "-90000000..90000000";
          }
        }
        leaf LockedLongitude {
          config false;
          description
          "This value is retained across reboots and is only
          reset after another scan completes successfully or
          {{param|GPSReset}} is set to {{true}}. If a scan has
          never succeeded before, the value 0 is reported.";
          type int32 {
            range "-180000000..180000000";
          }
        }
        leaf NumberOfSatellites {
          config false;
          description
          "This value is retained across reboots and is only
          reset after another scan completes successfully or
          {{param|GPSReset}} is set to {{true}}. If a scan has
          never succeeded before, the value 0 is reported.";
          type uint32;
        }
        leaf GPSReset {
          config true;
          description
          "Setting this to {{true}} will cause a reset on the
          GPS Hardware.  Setting this to {{false}} has no
          effect.";
          type boolean;
        }
        container ContinuousGPSStatus {
          description
          "When {{param|#.ContinuousGPS}} is {{false}}, the
          parameters in this object are not being updated and
          their values are not accurate.";
          leaf CurrentFix {
            config false;
            description
            "The value is {{true}} if the location fix is
            currently valid (i.e.  GPS receiver is currently
            tracking satellite signals), otherwise it is
            {{false}}. After a reboot the value is {{false}}
            until the GPS receivers has a valid current
            position.";
            type boolean;
          }
          leaf GotFix {
            config false;
            description
            "The GPS coordinates ({{param|Latitude}},
            {{param|Longitude}}, and {{param|Elevation}}) are
            not valid until {{param}} has a value of {{true}}.";
            type boolean;
          }
          leaf TimingGood {
            config false;
            description
            "The value is {{true}} if the timing synchronization
            is good, otherwise it is {{false}}. After a reboot
            the value is {{false}} until the timing is
            synchronized again.";
            type boolean;
          }
          leaf Latitude {
            config false;
            description
            "If the parameter has never been set before, the
            value 0 is reported.  The value SHOULD be
            maintained over a reboot.";
            type int32 {
              range "-90000000..90000000";
            }
          }
          leaf Longitude {
            config false;
            description
            "If the parameter has never been set before, the
            value 0 is reported.  The value SHOULD be
            maintained over a reboot.";
            type int32 {
              range "-180000000..180000000";
            }
          }
          leaf Elevation {
            config false;
            description
            "If the parameter has never been set before, the
            value 0 is reported.  The value SHOULD be
            maintained over a reboot.";
            type int32 {
              range "-5000000..25000000";
            }
          }
          leaf LastFixTime {
            config false;
            description
            "The Unknown Time value defined in
            {{bibref|TR-106a4|Section 3.2}} is used when
            {{param|GotFix}} is {{false}}. This applies too
            after a reboot of the device until a valid location
            is determined and {{param|GotFix}} transsitions to
            {{true}}.";
            type yang:date-and-time;
          }
          leaf LastFixDuration {
            config false;
            description
            "Number of {{units}} of continuous GPS fix time.
            After a reboot this value is reset to 0.";
            type uint32;
          }
          leaf FirstFixTimeout {
            config true;
            description
            "A value of -1 means that there is no timeout and no
            fault logging.";
            type int32 {
              range "-1..max";
            }
          }
          leaf SatellitesTracked {
            config false;
            description
            "The number of satellites the receiver is tracking.";
            type uint32;
          }
          leaf SatelliteTrackingInterval {
            config true;
            description
            "The interval in {{units}} at which the GPS tracking
            information gets reported.";
            type uint32 {
              range "60..3600";
            }
          }
          leaf ReceiverStatus {
            config false;
            description
            "The output of the GPS receiver's status.";
            type string {
              length "0..256";
            }
          }
          leaf LocationType {
            config false;
            description
            "Indicates whether the {{param|Latitude}},
            {{param|Longitude}}, and {{param|Elevation}} values
            are determined via a GPS Fix (where the value of
            this parameter would be {{enum|Real}}) or via some
            other means (where the value of this parameter
            would be {{enum|Reference}}).";
            type enumeration {
              enum "Real";
              enum "Reference";
            }
          }
          leaf LockTimeOutDuration {
            config true;
            description
            "The timer duration, in {{units}}, for which the
            device waits for GPS to acquire lock.";
            type uint32 {
              range "120..86400";
            }
          }
        }
        container AGPSServerConfig {
          description
          "This object contains parameters for the configuration
          of the Assisted Global Positioning System (A-GPS)
          server.  See also {{bibref|3GPP-TS.25.171|Section
          3.2}}";
          leaf Enable {
            config true;
            description
            "Enables or disables the {{object}} entry.";
            type boolean;
          }
          leaf ServerURL {
            config true;
            description
            "A-GPS server host name or IP address.";
            type string {
              length "0..256";
            }
          }
          leaf ServerPort {
            config true;
            description
            "The port to use when communicating to the A-GPS
            Server.";
            type uint32 {
              range "min..65535";
            }
          }
          leaf Username {
            config true;
            description
            "Username to be used by the device to authenticate
            with the A-GPS server.  This string is set to
            {{empty}} if no authentication is used.";
            type string {
              length "0..64";
            }
          }
          leaf Password {
            config true;
            description
            "Password to be used by the device to authenticate
            with the A-GPS server.  This string is set to
            {{empty}} if no authentication is used.";
            type string {
              length "0..64";
            }
          }
          leaf ReferenceLatitude {
            config true;
            description
            "Example: A latitude of 13d19.43' N would be
            represented as 13,323,833, derived as
            (13*1,000,000)+((19.43*1,000,000)/60).  Latitude of
            50d00.00' S would be represented as value
            -50,000,000.";
            type int32 {
              range "-90000000..90000000";
            }
          }
          leaf ReferenceLongitude {
            config true;
            description
            "Example: A longitude of 13d19.43' E would be
            represented as 13,323,833, derived as
            (13*1,000,000)+((19.43*1,000,000)/60). A longitude
            of 50d00'00'' W would be represented as value
            -50,000,000.";
            type int32 {
              range "-180000000..180000000";
            }
          }
          leaf ServerInUse {
            config false;
            description
            "After a reboot the value is {{false}} until the
            server could be contacted again.";
            type boolean;
          }
        }
      }
      container PerfMgmt {
        description
        "This object contains parameters relating to Performance
        Management in a Femto-related environment.";
        leaf ConfigNumberOfEntries {
          config false;
          description
          "{{numentries}}";
          type uint32;
        }
        list Config {
          key "URL PeriodicUploadInterval PeriodicUploadTime";
          unique "Alias";
          config true;
          description
          "This object contains parameters relating to File
          Management configuration for uploading of Performance
          Files to a designated File Server.  Each table entry
          can be referenced by zero or more radio-specific
          objects contained in the FAPService instances.  The
          periodic upload will upload data for all of the
          radio-specific objects that reference it.";
          leaf Enable {
            config true;
            description
            "Enables or disables this entry.  If this entry is
            disabled then its periodic uploads are not
            performed.";
            type boolean;
          }
          leaf Alias {
            config true;
            description
            "{{datatype|expand}}";
            type Alias;
          }
          leaf URL {
            config true;
            description
            "This argument specifies only the destination file
            location, and does not indicate in any way the name
            or location of the local file to be uploaded.";
            type string {
              length "0..256";
            }
          }
          leaf Username {
            config true;
            description
            "Username to be used by the device to authenticate
            with the file server.  This string is set to
            {{empty}} if no authentication is used.";
            type string {
              length "0..256";
            }
          }
          leaf Password {
            config true;
            description
            "Password to be used by the device to authenticate
            with the file server.  This string is set to
            {{empty}} if no authentication is used.";
            type string {
              length "0..256";
            }
          }
          leaf PeriodicUploadInterval {
            config true;
            description
            "The duration in {{units}} of the interval for which
            the device MUST create a Performance File and
            attempt to upload the file to {{param|URL}} if
            {{param|Enable}} is {{true}}.";
            type uint32 {
              range "1..max";
            }
          }
          leaf PeriodicUploadTime {
            config true;
            description
            "If absolute time is not available to the device,
            its periodic file upload behavior MUST be the same
            as if the {{param}} parameter was set to the
            Unknown Time value.";
            type yang:date-and-time;
          }
        }
      }
      container ApplicationPlatform {
        description
        "{{bibref|TR-262|appendix I}} provides the \"Theory of
        Operation\" for the usage of this object.";
        leaf Version {
          config false;
          description
          "Version of Femto Application Platform running on this
          device";
          type string {
            length "0..64";
          }
        }
        leaf Enable {
          config true;
          description
          "Enable or disable the Femto ApplicationPlatform";
          type boolean;
        }
        leaf Status {
          config false;
          description
          "Current state of the Femto Application Platform.";
          type enumeration {
            enum "Disabled" {
              description
              "The Femto Application Platform is not available";
            }
            enum "Enabled" {
              description
              "The Femto Application Platform is available";
            }
            enum "Reset" {
              description
              "The FemtoApplicationPlatform is in the process of
              being reset and will transition to the
              {{enum|Disabled}} state when the reset operation
              is completed";
            }
            enum "Initializing" {
              description
              "The FemtoApplicationPlatform is being initialized
              and will transition to the {{enum|Enabled}} state
              once the initialization is completed";
            }
          }
        }
        leaf MaxNumberOfApplications {
          config false;
          description
          "Determines how many Femtozone Applications can be
          supported by the Femto Application Platform
          simultaneously.";
          type uint32;
        }
        leaf CurrentNumberofApplications {
          config false;
          description
          "Specifies how many Femtozone Applications are
          currently communicating with the Femto Application
          Platform.";
          type uint32;
        }
        container Capabilities {
          description
          "This object contains parameters related to the
          capabilities of the Femtozone Application Platform
          and the Femtozone APIs.";
          leaf PresenceApplicationSupport {
            config false;
            description
            "Specifies whether the Femto Application Platform
            supports Presence-Based Femtozone Applications";
            type boolean;
          }
          leaf FemtoAwarenessAPISupport {
            config false;
            description
            "Specifies whether the Femto Awareness API is
            supported on this device.";
            type boolean;
          }
          leaf SMSAPISupport {
            config false;
            description
            "Specifies whether the SMS API is supported on this
            device.";
            type boolean;
          }
          leaf SubscribeToNotificationsOfSMSSentToApplicationSupport {
            config false;
            description
            "Specifies whether the
            SubscribeToNotificationsOfSMSSentToApplication
            functionality is supported by the FAP SMS API.";
            type boolean;
          }
          leaf QuerySMSDeliveryStatusSupport {
            config false;
            description
            "Specifies whether the QuerySMSDeliveryStatus
            functionality is supported by the FAP SMS API.";
            type boolean;
          }
          leaf MMSAPISupport {
            config false;
            description
            "Specifies whether the MMS API is supported on this
            device.";
            type boolean;
          }
          leaf QueryMMSDeliveryStatusSupport {
            config false;
            description
            "Specifies whether the QueryMMSDeliveryStatus
            functionality is supported by the FAP MMS API.";
            type boolean;
          }
          leaf SubscribeToNotificationsOfMMSSentToApplicationSupport {
            config false;
            description
            "Specifies whether the
            SubscribeToNotificationsOfMMSSentToApplication
            functionality is supported by the FAP MMS API.";
            type boolean;
          }
          leaf TerminalLocationAPISupport {
            config false;
            description
            "Specifies whether the Terminal Location API is
            supported on this device.";
            type boolean;
          }
          leaf-list AuthenticationMethodsSupported {
            config false;
            description
            "Specifies the supported methods that 3rd Party
            Applications can use to authenticate with the Femto
            Application Platform at initialization.  Comma
            separated list of strings.";
            type enumeration {
              enum "Basic";
              enum "Digest";
              enum "DigitalSignature";
            }
          }
          leaf-list AccessLevelsSupported {
            config false;
            description
            "Specifies the supported access levels that 3rd
            Party Applications can request when authenticating
            with the Femto Application Platform at
            initialization.  This access level is with respect
            to resources within the Femto Application Platform
            only (not to be confused with Access Mode parameter
            in .FAPService.{i}.AccessMgmt).";
            type enumeration {
              enum "Guest";
              enum "Standard";
              enum "Restricted";
              enum "Administrator";
              enum "Debug";
            }
          }
          leaf-list SendSMSTargetAddressType {
            config false;
            description
            "Specifies the supported types of addresses SMSs can
            be sent to.";
            type enumeration {
              enum "TelUri";
              enum "AnonymousReference";
              enum "All";
            }
          }
          leaf-list SendMMSTargetAddressType {
            config false;
            description
            "Specifies the supported types of addresses MMSs can
            be sent to.";
            type enumeration {
              enum "TelUri";
              enum "AnonymousReference";
              enum "All";
            }
          }
        }
        container Control {
          description
          "This object contains parameters related to the
          operation of the Femtozone APIs.";
          leaf AuthenticationMethod {
            config true;
            description
            "'''''Note:''''' The credentials are not part of the
            data model and have to be supplied externally.";
            type string {
              length "0..256";
            }
            must ". = ../../Capabilities/AuthenticationMethodsSupported";
          }
          leaf TunnelInst {
            config true;
            description
            "If the referenced object is deleted, the parameter
            value MUST be set to an empty string.";
            type string {
              length "0..256";
            }
          }
          container FemtoAwareness {
            description
            "This object contains parameters related to the
            Femto Awareness API.";
            leaf APIEnable {
              config true;
              description
              "Enable or disable FemtoAwareness API exposure on
              FAP";
              type boolean;
            }
            leaf QueueEnable {
              config true;
              description
              "Enable or disable Request queueing for the API";
              type boolean;
            }
            leaf Queueing {
              config true;
              description
              "Determines how FAP handles simultaneous requests
              from different Applications to Femto Awareness
              API.";
              type enumeration {
                enum "FiFo";
                enum "Priority";
              }
            }
            leaf MaxAPIUsersNumber {
              config true;
              description
              "Determines the Max Number of different
              Applications that can send Requests to Femto
              Awareness API.";
              type uint32 {
                range "0..255";
              }
            }
            leaf FemtozoneID {
              config true;
              description
              "Specifies Identifier of the Femtozone.";
              type string {
                length "0..256";
              }
            }
            leaf NotificationsUserIdentifierMSISDN {
              config true;
              description
              "Specifies whether the Mobile Station
              International Subscriber Directory Number
              (MSISDN) has to be used as UserIdentifier in
              Femto Awareness Notifications.  A value of
              {{true}} means that the MSISDN is send as user
              identifier, a value of {{false}} means that an
              anonymous reference is used.";
              type boolean;
            }
            leaf SubscribeToNotificationsResponseCallbackData {
              config true;
              description
              "Specifies whether the OPTIONAL Argument
              \"Callback Data\" has to be used in Responses to
              Requests to \"Subscribe To Femto Awareness
              Notifications\".";
              type boolean;
            }
            leaf QueryFemtocellResponseTimezone {
              config true;
              description
              "Specifies whether the OPTIONAL Argument
              \"Timezone\" has to be used in Responses to
              Requests to \"Query Femtocell Status\".";
              type boolean;
            }
          }
          container SMS {
            description
            "This object contains parameters related to the SMS
            API.";
            leaf APIEnable {
              config true;
              description
              "Enable or disable SMS API exposure on FAP";
              type boolean;
            }
            leaf QueueEnable {
              config true;
              description
              "Enable or disable Request queueing for the API";
              type boolean;
            }
            leaf Queueing {
              config true;
              description
              "Determines how FAP handles simultaneous requests
              from different Applications to SMS API.";
              type enumeration {
                enum "FiFo";
                enum "Priority";
              }
            }
            leaf MaxAPIUsersNumber {
              config true;
              description
              "Determines the Max Number of different
              Applications that can send Requests to SMS API.";
              type uint32 {
                range "0..255";
              }
            }
            leaf MinSendSMSTimeInterval {
              config true;
              description
              "Determines the Minimum Time Interval in {{units}}
              between two consecutive Send SMS Requests by the
              same Application.";
              type uint32 {
                range "0..3599";
              }
            }
            leaf EnableQuerySMSDeliveryStatus {
              config true;
              description
              "Enable or disable \"QuerySMSDeliveryStatus\"
              Operation on SMS API. When disabled,
              QuerySMSDeliveryStatus Requests to SMS API are
              ignored.";
              type boolean;
            }
            leaf EnableSubscribeToNotificationsOfMessageSentToApplication {
              config true;
              description
              "Enable or disable
              \"SubscribeToNotificationsOfMessageSentToApplication\"
              Operation on SMS API. When disabled, SubscribeTo
              NotificationsOfMessageSentToApplication Requests
              to SMS API are ignored.";
              type boolean;
            }
          }
          container MMS {
            description
            "This object contains parameters related to the MMS
            API.";
            leaf APIEnable {
              config true;
              description
              "Enable or disable MMS API exposure on FAP";
              type boolean;
            }
            leaf QueueEnable {
              config true;
              description
              "Enable or disable Request queueing for the API";
              type boolean;
            }
            leaf Queueing {
              config true;
              description
              "Determines how FAP handles simultaneous requests
              from different Applications to MMS API.";
              type enumeration {
                enum "FiFo";
                enum "Priority";
              }
            }
            leaf MaxAPIUsersNumber {
              config true;
              description
              "Determines the Max Number of different
              Applications that can send Requests to MMS API.";
              type uint32 {
                range "0..255";
              }
            }
            leaf MinSendMMSTimeInterval {
              config true;
              description
              "Determines the Minimum Time Interval in {{units}}
              between two consecutive Send MMS Requests by the
              same Application.";
              type uint32 {
                range "0..3599";
              }
            }
            leaf EnableQueryMMSDeliveryStatus {
              config true;
              description
              "Enable or disable \"QuerySMSDeliveryStatus\"
              Operation on MMS API. When disabled,
              QuerySMSDeliveryStatus Requests to MMS API are
              ignored.";
              type boolean;
            }
            leaf EnableSubscribeToNotificationsOfMessageSentToApplication {
              config true;
              description
              "Enable or disable \"SubscribeTo
              NotificationsOfMessageSentToApplication\"
              Operation on MMS API. When disabled, SubscribeTo
              NotificationsOfMessageSentToApplication Requests
              to MMS API are ignored.";
              type boolean;
            }
          }
          container TerminalLocation {
            description
            "This object contains parameters related to the
            TerminalLocation API.";
            leaf APIEnable {
              config true;
              description
              "Enable or disable TerminalLocation API exposure
              on FAP";
              type boolean;
            }
            leaf QueueEnable {
              config true;
              description
              "Enable or disable Request queueing for the API";
              type boolean;
            }
            leaf Queueing {
              config true;
              description
              "Determines how FAP handles simultaneous requests
              from different Applications to TerminalLocation
              API.";
              type enumeration {
                enum "FiFo";
                enum "Priority";
              }
            }
            leaf MaxAPIUsersNumber {
              config true;
              description
              "Determines the Max Number of different
              Applications that can send Requests to
              TerminalLocation API.";
              type uint32 {
                range "0..255";
              }
            }
            leaf QueryMobileLocationResponseAddress {
              config true;
              description
              "Specifies Terminal Address  Format to be used in
              QueryMobileLocation Responses.";
              type enumeration {
                enum "TelUri";
                enum "AnonymousReference";
              }
            }
            leaf QueryMobileLocationResponseLongitudeLatitude {
              config true;
              description
              "Include or exclude FAP Longitude and Latitude
              arguments in Responses to QueryMobileLocation
              Requests.";
              type boolean;
            }
            leaf QueryMobileLocationResponseAltitude {
              config true;
              description
              "Include or exclude FAP Altitude argument in
              Responses to QueryMobileLocation Requests .";
              type boolean;
            }
            leaf QueryMobileLocationResponseTimestamp {
              config true;
              description
              "Specifies Response Timestamp in {{units}}.";
              type uint32 {
                range "0..86399";
              }
            }
          }
        }
        container Monitoring {
          description
          "This object contains parameters related to the
          monitoring of the Femtozone Application Platform and
          the Femtozone APIs.";
          leaf Enable {
            config true;
            description
            "Enables and disables this entry.";
            type boolean;
          }
          leaf MonitoringInterval {
            config true;
            description
            "Specifies the interval in {{units}} used to collect
            the monitoring measurements.";
            type uint32;
          }
          leaf AuthenticationRequestsReceived {
            config false;
            description
            "Specifies the total number of authentication
            requests received by the Femto Application
            Platform.  The counter will be reset whenever the
            device reboots or the {{param|Enable}} parameter is
            set to {{true}}.";
            type uint32;
          }
          leaf AuthenticationRequestsRejected {
            config false;
            description
            "Specifies the number of authentication requests
            received by the Femto Application Platform that
            were rejected.  The counter will be reset whenever
            the device reboots or the {{param|Enable}}
            parameter is set to {{true}}.";
            type uint32;
          }
          container FemtoAwareness {
            description
            "This object contains parameters related to the
            Monitoring of the FemtoAwareness API.";
            leaf APIAvailable {
              config false;
              description
              "Specifies whether the FemtoAwareness API is
              currently available on this device (the API could
              be disabled or could have exhausted its
              resources)";
              type boolean;
            }
            leaf APIUsers {
              config false;
              description
              "Specifies the current number of Applications
              using the Femto Awareness API.";
              type uint32 {
                range "0..255";
              }
            }
            leaf QueueState {
              config false;
              description
              "Specifies the state of the Femto Awareness API
              Queue.";
              type enumeration {
                enum "Disabled";
                enum "Ready";
                enum "Flushed";
              }
            }
            leaf QueueNum {
              config false;
              description
              "Specifies the current number of requests waiting
              in the Femto Awareness API Queue.";
              type uint32 {
                range "0..255";
              }
            }
            leaf QueueReceived {
              config false;
              description
              "Specifies the number of requests in the Femto
              Awareness API Queue that have been received.  The
              counter will be reset whenever the device reboots
              or the {{param|#.Enable}} parameter is set to
              {{true}}.";
              type uint32;
            }
            leaf QueueDiscarded {
              config false;
              description
              "Specifies the number of requests in the Femto
              Awareness API Queue that have been discarded.
              The counter will be reset whenever the device
              reboots or the {{param|#.Enable}} parameter is
              set to {{true}}.";
              type uint32;
            }
          }
          container SMS {
            description
            "This object contains parameters related to the
            Monitoring of the SMS API.";
            leaf APIAvailable {
              config false;
              description
              "Specifies whether the SMS API is currently
              available on this device (the API could be
              disabled or could have exhausted its resources)..";
              type boolean;
            }
            leaf APIUsers {
              config false;
              description
              "Specifies the current number of Applications
              using the SMS API.";
              type uint32 {
                range "0..255";
              }
            }
            leaf QueueState {
              config false;
              description
              "Specifies the state of the SMS API Queue.";
              type enumeration {
                enum "Disabled";
                enum "Ready";
                enum "Flushed";
              }
            }
            leaf QueueNum {
              config false;
              description
              "Specifies the current number of requests waiting
              in the SMS API Queue.";
              type uint32 {
                range "0..255";
              }
            }
            leaf QueueReceived {
              config false;
              description
              "Specifies the number of requests in the SMS API
              Queue that have been received.  The counter will
              be reset whenever the device reboots or the
              {{param|#.Enable}} parameter is set to {{true}}.";
              type uint32;
            }
            leaf QueueDiscarded {
              config false;
              description
              "Specifies the number of requests in the SMS API
              Queue that have been discarded.  The counter will
              be reset whenever the device reboots or the
              {{param|#.Enable}} parameter is set to {{true}}.";
              type uint32;
            }
          }
          container MMS {
            description
            "This object contains parameters related to the
            Monitoring of the MMS API.";
            leaf APIAvailable {
              config false;
              description
              "Specifies whether the MMS API is currently
              available on this device (the API could be
              disabled or could have exhausted its resources)..";
              type boolean;
            }
            leaf APIUsers {
              config false;
              description
              "Specifies the current number of Applications
              using the MMS API.";
              type uint32 {
                range "0..255";
              }
            }
            leaf QueueState {
              config false;
              description
              "Specifies the state of the MMS API Queue.";
              type enumeration {
                enum "Disabled";
                enum "Ready";
                enum "Flushed";
              }
            }
            leaf QueueNum {
              config false;
              description
              "Specifies the current number of requests waiting
              in the MMS API Queue.";
              type uint32 {
                range "0..255";
              }
            }
            leaf QueueReceived {
              config false;
              description
              "Specifies the number of requests in the MMS API
              Queue that have been received.  The counter will
              be reset whenever the device reboots or the
              {{param|#.Enable}} parameter is set to {{true}}.";
              type uint32;
            }
            leaf QueueDiscarded {
              config false;
              description
              "Specifies the number of requests in the MMS API
              Queue that have been discarded.  The counter will
              be reset whenever the device reboots or the
              {{param|#.Enable}} parameter is set to {{true}}.";
              type uint32;
            }
          }
          container TerminalLocation {
            description
            "This object contains parameters related to the
            Monitoring of the TerminalLocation API.";
            leaf APIAvailable {
              config false;
              description
              "Specifies whether the TerminalLocation API is
              currently available on this device (the API could
              be disabled or could have exhausted its
              resources)..";
              type boolean;
            }
            leaf APIUsers {
              config false;
              description
              "Specifies the current number of Applications
              using the Terminal Location API.";
              type uint32 {
                range "0..255";
              }
            }
            leaf QueueState {
              config false;
              description
              "Specifies the state of the Terminal Location API
              Queue.";
              type enumeration {
                enum "Disabled";
                enum "Ready";
                enum "Flushed";
              }
            }
            leaf QueueNum {
              config false;
              description
              "Specifies the current number of requests waiting
              in the Terminal Location API Queue.";
              type uint32 {
                range "0..255";
              }
            }
            leaf QueueReceived {
              config false;
              description
              "Specifies the number of requests in the Terminal
              Location API Queue that have been received.  The
              counter will be reset whenever the device reboots
              or the {{param|#.Enable}} parameter is set to
              {{true}}.";
              type uint32;
            }
            leaf QueueDiscarded {
              config false;
              description
              "Specifies the number of requests in the Terminal
              Location API Queue that have been discarded.  The
              counter will be reset whenever the device reboots
              or the {{param|#.Enable}} parameter is set to
              {{true}}.";
              type uint32;
            }
          }
        }
      }
    }
    container BulkData {
      description
      "The Bulk Data Collection Profiles are measured over a
      reporting interval (which can be aligned with absolute
      time) and are made available to the collection server.";
      leaf Enable {
        config true;
        description
        "If {{false}}, bulk data will not be collected or
        reported.";
        type boolean;
      }
      leaf Status {
        config false;
        description
        "Indicates the status of the Bulk Data Collection
        mechanism.";
        type enumeration {
          enum "Enabled" {
            description
            "Bulk Data Collection is enabled and working as
            intended.";
          }
          enum "Disabled" {
            description
            "Bulk Data Collection is disabled.";
          }
          enum "Error" {
            description
            "Bulk Data Collection is enabled, but there is an
            error condition preventing the successful
            collection of bulk data.";
          }
        }
      }
      leaf MinReportingInterval {
        config false;
        description
        "A value of 0 indicates no minimum reporting interval.";
        type uint32;
      }
      leaf-list Protocols {
        config false;
        description
        "Represents the IPDR and transport protocols that this
        device is capable of supporting.";
        type enumeration {
          enum "Streaming" {
            description
            "IPDR Streaming Protocol {{bibref|IPDR-SP}}";
          }
          enum "File" {
            description
            "IPDR File Transfer Protocol {{bibref|IPDR-FTP}}";
          }
          enum "HTTP" {
            description
            "Hypertext Transfer Protocol {{bibref|RFC2616}}";
          }
        }
      }
      leaf-list EncodingTypes {
        config false;
        description
        "Represents the Encoding Types for the protocols that
        this device is capable of supporting.";
        type enumeration {
          enum "XML" {
            description
            "Used with the IPDR Streaming and File Protocols.
            {{bibref|IPDR-XML}}";
          }
          enum "XDR" {
            description
            "Used with the IPDR Streaming and File Protocols.
            {{bibref|IPDR-XDR}}";
          }
          enum "CSV" {
            description
            "Comma Separated Values.  Used with the HTTP
            Protocol.  {{bibref|RFC4180}}";
          }
          enum "JSON" {
            description
            "JavaScript Object Notation.  Used with the HTTP
            Protocol {{bibref|RFC7159}}";
          }
        }
      }
      leaf ParameterWildCardSupported {
        config false;
        description
        "When {{true}}, the Device supports the use of wildcards
        to determine the parameters that are reported using a
        Profile.";
        type boolean;
      }
      leaf MaxNumberOfProfiles {
        config false;
        description
        "If the value of this parameter is -1, then it means
        that the CPE doesn't have a limit to the number of
        profiles that can exist.";
        type int32 {
          range "-1..max";
        }
      }
      leaf MaxNumberOfParameterReferences {
        config false;
        description
        "If the value of this parameter is -1, then it means
        that the CPE doesn't have a limit to the number of
        parameter that can be referenced via the bulk data
        collection mechanism.";
        type int32 {
          range "-1..max";
        }
      }
      leaf ProfileNumberOfEntries {
        config false;
        description
        "{{numentries}}";
        type uint32;
      }
      list Profile {
        key "Alias";
        config true;
        description
        "Each profile represents a bulk data report, including
        its own timing configuration, communications
        configuration, and set of parameters.  This allows the
        ACS to configure multiple reports to be generated at
        different times for different sets of data.";
        leaf Enable {
          config true;
          description
          "If {{false}}, this profile will not be collected or
          reported.";
          type boolean;
          default "false";
        }
        leaf Alias {
          config true;
          description
          "{{datatype|expand}}";
          type Alias;
        }
        leaf Name {
          config true;
          description
          "The name of the profile.";
          type string {
            length "0..255";
          }
        }
        leaf NumberOfRetainedFailedReports {
          config true;
          description
          "A value of -1 indicates that the CPE will retain as
          many failed reports as possible.";
          type int32 {
            range "-1..max";
          }
          default "0";
        }
        leaf Protocol {
          config true;
          description
          "The Bulk Data Protocol being used for this collection
          profile.";
          type string;
          must ". = ../../Protocols";
        }
        leaf EncodingType {
          config true;
          description
          "The Bulk Data encoding type being used for this
          collection profile.";
          type string;
          must ". = ../../EncodingTypes";
        }
        leaf ReportingInterval {
          config true;
          description
          "For example, if {{param}} is 86400 (a day) and if
          {{param|TimeReference}} is set to UTC midnight on
          some day (in the past, present, or future) then the
          CPE will generate (and transmit, if the
          {{param|Protocol}} parameter is set to
          {{enum|Streaming|#.Protocols}}) its report at
          midnight every 24 hours.";
          type uint32 {
            range "1..max";
          }
          default "86400";
        }
        leaf TimeReference {
          config true;
          description
          "Note that, if {{param}} is set to a time other than
          the Unknown Time, the first reporting interval (which
          has to begin immediately) will almost certainly be
          shorter than {{param|ReportingInterval}}).  This is
          why {{param}} is defined in terms of when reporting
          intervals complete rather than start.";
          type yang:date-and-time;
          default "0001-01-01T00:00:00Z";
        }
        leaf StreamingHost {
          config true;
          description
          "This is the host name or IP Address of the IPDR
          Collector to be used by the CPE to stream bulk data
          records if this collection profile is configured for
          the IPDR Streaming Protocol {{bibref|IPDR-SP}} (the
          {{param|Protocol}} parameter has a value of
          {{enum|Streaming|#.Protocols}}).";
          type string {
            length "0..256";
          }
        }
        leaf StreamingPort {
          config true;
          description
          "This is the port number of the IPDR Collector to be
          used by the CPE to stream bulk data records if this
          collection profile is configured for the IPDR
          Streaming Protocol {{bibref|IPDR-SP}} (the
          {{param|Protocol}} parameter has a value of
          {{enum|Streaming|#.Protocols}}).";
          type uint32 {
            range "0..65535";
          }
          default "4737";
        }
        leaf StreamingSessionID {
          config true;
          description
          "Within the IPDR Streaming Protocol specification the
          Session ID has a type of a single 'char', but we are
          restricting the range even further (ASCII values of
          '0' - '9' and 'A' - 'Z'.";
          type uint32 {
            range "48..57|65..90";
          }
        }
        leaf FileTransferURL {
          config true;
          description
          "This is the URL within the CPE that is used by an
          IPDR Collector to retrieve the IPDRDocs when this
          collection profile is configured for the IPDR File
          Transfer Protocol {{bibref|IPDR-FTP}} (the
          {{param|Protocol}} parameter has a value of
          {{enum|File|#.Protocols}}).";
          type string {
            length "0..256";
          }
        }
        leaf FileTransferUsername {
          config true;
          description
          "This is the {{param}} that the IPDR Collector uses to
          access the CPE when this collection profile is
          configured for the IPDR File Transfer Protocol
          {{bibref|IPDR-FTP}} (the {{param|Protocol}} parameter
          has a value of {{enum|File|#.Protocols}}).";
          type string {
            length "0..64";
          }
        }
        leaf FileTransferPassword {
          config true;
          description
          "This is the {{param}} that the IPDR Collector uses to
          access the CPE when this collection profile is
          configured for the IPDR File Transfer Protocol
          {{bibref|IPDR-FTP}} (the {{param|Protocol}} parameter
          has a value of {{enum|File|#.Protocols}}).";
          type string {
            length "0..64";
          }
        }
        leaf ControlFileFormat {
          config true;
          description
          "For example, BulkData_NNNN.log where \"BulkData\"
          would be the prefix, \"NNNN\" would be the policy,
          and \"log\" would be the suffix.  Files adhering to
          this file format would look like: BulkData_0000.log,
          BulkData_0001.log, etc.";
          type string {
            length "0..128";
          }
        }
        leaf ParameterNumberOfEntries {
          config false;
          description
          "{{numentries}}";
          type uint32;
        }
        list Parameter {
          key "_id";
          leaf "_id" {
            type "uint32";
          }
          config true;
          description
          "Each entry in this table represents a parameter (or
          set of parameters if a partial path is provided) to
          be collected and reported.";
          leaf Name {
            config true;
            description
            "When the value {{param|Reference}} parameter
            contains wildcards and/or partial parameter names,
            the rules for determining the value of this
            parameter are specified in {{bibref|TR-157a10|Annex
            A.3.2.1}}.";
            type string {
              length "0..64";
            }
          }
          leaf Reference {
            config true;
            description
            "In the case where a partial parameter path is
            specified, the sub-objects of the resolved pattern
            and contained parameters will be part of the bulk
            data collected and reported.  If the path name
            refers to an object then it MUST end with a '.'.";
            type string {
              length "0..256";
            }
          }
        }
        container CSVEncoding {
          description
          "This object defines the properties to be used when
          the {{object|##.Profile}} object's
          {{param|#.EncodingType}} parameter value is
          {{enum|CSV|##.EncodingTypes}}.";
          leaf FieldSeparator {
            config true;
            description
            "Field separator to use when encoding CSV data.";
            type string;
            default ",";
          }
          leaf RowSeparator {
            config true;
            description
            "Row separator to use when encoding CSV data.";
            type string;
            default "";
          }
          leaf EscapeCharacter {
            config true;
            description
            "Escape character to use when encoding CSV data.";
            type string;
            default "\"";
          }
          leaf ReportFormat {
            config true;
            description
            "Note: This parameter is encoded as a token in the
            BBF-Report-Format header field and MUST NOT include
            spaces or other characters excluded from token
            characters defined in {{bibref|RFC2616}}.";
            type enumeration {
              enum "ParameterPerRow" {
                description
                "Reports are formatted with each parameter
                formatted as a row entry.";
              }
              enum "ParameterPerColumn" {
                description
                "Reports are formatted with each parameter
                formatted as a column entry.";
              }
            }
            default "ParameterPerColumn";
          }
          leaf RowTimestamp {
            config true;
            description
            "The format of the timestamp to use for data
            inserted into the row.";
            type enumeration {
              enum "Unix-Epoch" {
                description
                "Timestamp is inserted using the UNIX epoch time
                (milliseconds since Jan 1, 1970 UTC) timestamp
                format.  If the CPE is unable to acquire a
                time, then the time that has elapsed since the
                last reboot of the device is used.";
              }
              enum "ISO-8601" {
                description
                "Timestamp is inserted using the ISO-8601
                timestamp format.  If the CPE is unable to
                acquire a time, then the processing described
                by the dateTime type in {{bibref|TR-069|Table
                12}} is followed.";
              }
              enum "None" {
                description
                "Timestamp is not inserted in the row.";
              }
            }
            default "Unix-Epoch";
          }
        }
        container JSONEncoding {
          description
          "This object defines the properties to be used when
          the {{object|##.Profile}} object's
          {{param|#.EncodingType}} parameter value is
          {{enum|JSON|##.EncodingTypes}}.";
          leaf ReportFormat {
            config true;
            description
            "Note: This parameter is encoded as a token in the
            BBF-Report-Format header field and MUST NOT include
            spaces or other characters excluded from token
            characters defined in {{bibref|RFC2616}}.";
            type enumeration {
              enum "ObjectHierarchy" {
                description
                "Reports are formatted with each object in the
                object hierarchy of the data model encoded as a
                corresponding hierarchy of JSON Objects with
                the parameters of the object specified as
                name/value pairs of the JSON Object.";
              }
              enum "NameValuePair" {
                description
                "Reports are formatted with each parameter of
                the data model encoded as a corresponding array
                of JSON Objects with the parameters specified
                as name/value pairs.";
              }
            }
            default "ObjectHierarchy";
          }
          leaf ReportTimestamp {
            config true;
            description
            "The format of timestamp to use for the JSON Object
            named \"CollectionTime\" as described in
            {{bibref|TR-157a10}}.";
            type enumeration {
              enum "Unix-Epoch" {
                description
                "Timestamp is inserted using the UNIX epoch time
                (milliseconds since Jan 1, 1970 UTC) timestamp
                format.  If the CPE is unable to acquire a
                time, then the time that has elapsed since the
                last reboot of the device is used.";
              }
              enum "ISO-8601" {
                description
                "Timestamp is inserted using the ISO-8601
                timestamp format.  If the CPE is unable to
                acquire a time, then the processing described
                by the dateTime type in {{bibref|TR-069|Table
                12}} is followed.";
              }
              enum "None" {
                description
                "Timestamp is not inserted.";
              }
            }
            default "Unix-Epoch";
          }
        }
        container HTTP {
          description
          "This object defines the properties to be used when
          transporting bulk data using the HTTP/HTTPS protocol.
          This object is used when the {{param|#.Protocol}}
          parameter has a value of {{enum|HTTP|##.Protocols}}.
          For authentication purposes the CPE MUST support HTTP
          Basic and Digest Access Authentication as defined in
          {{bibref|RFC2616}}.";
          leaf URL {
            config true;
            description
            "The URL, as defined in {{bibref|RFC3986}}, for the
            collection server to receive the Bulk Data
            transmitted by the CPE.";
            type string {
              length "0..1024";
            }
          }
          leaf Username {
            config true;
            description
            "Username used to authenticate the CPE when making a
            connection to the collection server.";
            type string {
              length "0..256";
            }
          }
          leaf Password {
            config true;
            description
            "Password used to authenticate the CPE when making a
            connection to the collection server.";
            type string {
              length "0..256";
            }
          }
          leaf-list CompressionsSupported {
            config false;
            description
            "Indicates the HTTP Compression mechanism(s)
            supported by this CPE for the purposes of
            transferring bulk data.";
            type enumeration {
              enum "GZIP" {
                description
                "As defined in {{bibref|RFC2616|Section 3.5}}";
              }
              enum "Compress" {
                description
                "As defined in {{bibref|RFC2616|Section 3.5}}";
              }
              enum "Deflate" {
                description
                "As defined in {{bibref|RFC2616|Section 3.5}}";
              }
            }
          }
          leaf Compression {
            config true;
            description
            "The value of this parameter represents the HTTP
            Compression mechanism to be used by the CPE when
            transferring data to the collection server.";
            type string;
            default "None";
            must ". = ../CompressionsSupported";
          }
          leaf-list MethodsSupported {
            config false;
            description
            "Indicates the HTTP method(s) supported by this CPE
            for the purposes of transferring bulk data.";
            type enumeration {
              enum "POST" {
                description
                "As defined in {{bibref|RFC2616|Section 9.5}}";
              }
              enum "PUT" {
                description
                "As defined in {{bibref|RFC2616|Section 9.6}}";
              }
            }
          }
          leaf Method {
            config true;
            description
            "The value of this parameter represents the HTTP
            method to be used by the CPE when transferring data
            to the collection server.";
            type string;
            default "POST";
            must ". = ../MethodsSupported";
          }
          leaf UseDateHeader {
            config true;
            description
            "When {{true}}, the CPE encodes the HTTP Date Header
            {{bibref|RFC2616|Section 14.18}} in the HTTP client
            request.";
            type boolean;
            default "true";
          }
          leaf RetryEnable {
            config true;
            description
            "When {{true}}, the CPE retries unsuccessful
            attempts to transfer data.";
            type boolean;
            default "false";
          }
          leaf RetryMinimumWaitInterval {
            config true;
            description
            "The device MUST use a random value between
            {{param}}  and ({{param}} *
            {{param|RetryIntervalMultiplier}} / 1000) as the
            first retry wait interval.  Other values in the
            retry pattern MUST be calculated using this value
            as a starting point.";
            type uint32 {
              range "1..65535";
            }
            default "5";
          }
          leaf RetryIntervalMultiplier {
            config true;
            description
            "The device MUST use a random value between
            {{param|RetryMinimumWaitInterval}}  and
            ({{param|RetryMinimumWaitInterval}} * {{param}} /
            1000) as the first retry wait interval.  Other
            values in the retry pattern MUST be calculated
            using this value as a starting point.";
            type uint32 {
              range "1000..65535";
            }
            default "2000";
          }
          leaf RequestURIParameterNumberOfEntries {
            config false;
            description
            "{{numentries}}";
            type uint32;
          }
          leaf PersistAcrossReboot {
            config true;
            description
            "If {{param}} is {{false}}, then failed data
            transfers are not required to be persisted across
            reboots.";
            type boolean;
            default "false";
          }
          list RequestURIParameter {
            key "_id";
            leaf "_id" {
              type "uint32";
            }
            config true;
            description
            "This object represents an instance of a parameter
            to be used in the report header used as part of the
            HTTP Request-URI transmitted by the CPE to the
            collection server using the Request-URI in addition
            to the parameters required by
            {{bibref|TR-157a10|Annex A.2.1}}.";
            leaf Name {
              config true;
              description
              "If {{param}} is {{empty}}, the name of the
              Request-URI parameter is the value of
              {{param|Reference}}.";
              type string {
                length "0..64";
              }
            }
            leaf Reference {
              config true;
              description
              "If the value of this parameter is empty, then
              this object is not encoded in the report header.";
              type string {
                length "0..256";
              }
            }
          }
        }
      }
    }
    container XMPP {
      description
      "The {{object}} represents the XMPP capabilities of the
      device as described in {{bibref|TR-069a5|Appendix III}}.";
      leaf ConnectionNumberOfEntries {
        config false;
        description
        "{{numentries}}";
        type uint32;
      }
      leaf-list SupportedServerConnectAlgorithms {
        config false;
        description
        "The algorithms supported by the CPE for resolving XMPP
        server addresses and ports.  {{enum}}";
        type enumeration {
          enum "DNS-SRV" {
            description
            "Use the preferred connection algorithm as specified
            in {{bibref|RFC6120|Section 3.2.1}} where the value
            of the {{param|Connection.{i}.Domain}} parameter is
            used to look up the server address and port to use.";
          }
          enum "DNS" {
            description
            "Use the fallback connection mechanism as specified
            in {{bibref|RFC6120|Section 3.2.2}}, where the
            value of the {{param|Connection.{i}.Domain}}
            parameter is used to look up the server address,
            and the port is the ''xmpp-client'' port (5222).";
          }
          enum "ServerTable" {
            description
            "Use the instances of the
            {{object|Connection.{i}.Server}} table based on the
            values of the
            {{param|Connection.{i}.Server.{i}.Priority}} and
            {{param|Connection.{i}.Server.{i}.Weight}}
            parameters as the basis for reconnect.  Instances
            MUST be reachable and reachable instances with the
            lowest value MUST be preferred.";
          }
          enum "WebSocket" {
            description
            "Use the discovery and connection algorithm as
            specified in {{bibref|RFC7395|Section 4}} where the
            value of the {{param|Connection.{i}.Domain}}
            parameter is used to create a secure HTTP request
            to discover the URL to use for the XMPP over
            WebSocket connection.";
          }
        }
      }
      list Connection {
        key "Username Domain Resource";
        unique "Alias";
        config true;
        description
        "The {{object}} represents a XMPP connection between the
        device and a server.  The {{param|Username}},
        {{param|Domain}} and {{param|Resource}} comprise the
        full identity (JabberID) of this {{object}} for this
        device.";
        leaf Enable {
          config true;
          description
          "This parameter is based on ''ifAdminStatus'' from
          {{bibref|RFC2863}}.";
          type boolean;
          default "false";
        }
        leaf Alias {
          config true;
          description
          "{{datatype|expand}}";
          type Alias;
        }
        leaf Username {
          config true;
          description
          "The proposed local-part of the Jabber ID of this
          {{object}}, and the value to be used to authenticate
          this {{object}} when making a connection to the
          Server using the procedure outlined in
          {{bibref|RFC6120|Section 6}}.";
          type string {
            length "0..256";
          }
        }
        leaf Password {
          config true;
          description
          "Note that on a factory reset of the CPE, the value of
          this parameter might be reset to its factory value.
          If an ACS modifies the  value of this parameter, it
          SHOULD be prepared to accommodate the situation that
          the original value is restored as the result of a
          factory reset.";
          type string {
            length "0..256";
          }
        }
        leaf Domain {
          config true;
          description
          "The proposed domain-part of the Jabber ID of this
          {{object}}.";
          type string {
            length "0..64";
          }
        }
        leaf Resource {
          config true;
          description
          "The proposed resource-part of the Jabber ID of this
          {{object}}.";
          type string {
            length "0..64";
          }
        }
        leaf JabberID {
          config false;
          description
          "The complete Jabber ID as determined by the first-hop
          XMPP server at time of connection establishment.
          This Jabber ID will usually be the standard
          concatentation of the local-part (Username),
          domain-part (Domain), and resource-part (Resource) as
          defined in {{bibref|RFC6120|Section 2.1}}
          (local-part@domain-part/resource-part), but since the
          Jabber ID is owned by the first-hop XMPP Server there
          are cases where the value will be different.";
          type string;
        }
        leaf Status {
          config false;
          description
          "When {{param|Enable}} is changed to {{true}} then
          {{param}} SHOULD change to {{enum|Enabled}} if and
          only if the interface is able to transmit and receive
          PDUs; it SHOULD change to {{enum|Dormant}} if and
          only if the interface is operable but is waiting for
          external actions before it can transmit and receive
          network traffic (and subsequently change to
          {{enum|Enabled}} if still operable when the expected
          actions have completed);  it SHOULD change to
          {{enum|Unknown}} if the state of the interface can
          not be determined for some reason.";
          type enumeration {
            enum "Enabled";
            enum "Disabled";
            enum "Unknown";
            enum "Dormant";
            enum "Connecting";
            enum "ServerNotPresent";
            enum "Error_Misconfigured";
            enum "Error_AuthenticationFailure";
            enum "Error";
          }
        }
        leaf LastChangeDate {
          config false;
          description
          "The date and time at which this {{object}} entered
          into its current operational state.";
          type yang:date-and-time;
        }
        leaf ServerConnectAlgorithm {
          config true;
          description
          "The algorithm the {{object}} uses when connecting
          with the associated lists of servers.";
          type string;
          default "DNS-SRV";
          must ". = ../../SupportedServerConnectAlgorithms";
        }
        leaf KeepAliveInterval {
          config true;
          description
          "{{bibref|RFC6120|Section 4.6.4}} recommends not
          checking more frequently than every 5 minutes (or 300
          {{units}}).";
          type int64 {
            range "-1..max";
          }
          default "-1";
        }
        leaf ServerConnectAttempts {
          config true;
          description
          "NOTE: If the value of this parameter is 0, server
          connection and reconnection behavior is
          implementation-dependent.";
          type uint32;
          default "16";
        }
        leaf ServerRetryInitialInterval {
          config true;
          description
          "NOTE: If the value of the
          {{param|ServerConnectAttempts}} parameter is 0, the
          value of this parameter is ignored.";
          type uint32 {
            range "1..65535";
          }
          default "60";
        }
        leaf ServerRetryIntervalMultiplier {
          config true;
          description
          "NOTE: If the value of the
          {{param|ServerConnectAttempts}} parameter is 0, the
          value of this parameter is ignored.";
          type uint32 {
            range "1000..65535";
          }
          default "2000";
        }
        leaf ServerRetryMaxInterval {
          config true;
          description
          "NOTE: If the value of the
          {{param|ServerConnectAttempts}} parameter is 0, the
          value of this parameter is ignored.";
          type uint32 {
            range "1..max";
          }
          default "30720";
        }
        leaf UseTLS {
          config true;
          description
          "If the value of {{param}} is {{false}} then the CPE
          will not initiate TLS negotiation if not required to
          by the XMPP Server.";
          type boolean;
          default "false";
        }
        leaf TLSEstablished {
          config false;
          description
          "If this XMPP Connection is either not established or
          established but not secured by TLS then the value of
          this parameter is {{false}}.";
          type boolean;
        }
        leaf ServerNumberOfEntries {
          config false;
          description
          "{{numentries}}";
          type uint32;
        }
        list Server {
          key "ServerAddress Port";
          unique "Alias";
          config true;
          description
          "This table is only relevant when
          {{param|##.Connection.{i}.ServerConnectAlgorithm}} is
          set to
          {{enum|ServerTable|##.Connection.{i}.ServerConnectAlgorithm}}.
          If {{param|##.Connection.{i}.ServerConnectAlgorithm}}
          is set to
          {{enum|DNS-SRV|##.Connection.{i}.ServerConnectAlgorithm}}
          then any instances of this table are ignored by this
          {{object|##.Connection}}.";
          leaf Enable {
            config true;
            description
            "This parameter is based on ''ifAdminStatus'' from
            {{bibref|RFC2863}}.";
            type boolean;
            default "false";
          }
          leaf Alias {
            config true;
            description
            "{{datatype|expand}}";
            type Alias;
          }
          leaf Priority {
            config true;
            description
            "The priority of this {{object}} that is used by the
            {{object|##.Connection}} when determining the
            {{object}} to connect.  The
            {{object|##.Connection}} MUST contact the
            {{object}} with the lowest-numbered priority that
            the {{object|##.Connection}} can reach as defined
            in {{bibref|RFC2782}}. The selection of {{object}}s
            with the same {{param}} value utilizes the
            {{param|Weight}} parameter to determine which
            {{object}} is selected by the
            {{object|##.Connection}}.";
            type uint32 {
              range "0..65535";
            }
          }
          leaf Weight {
            config true;
            description
            "This parameter specifies a relative weight for
            entries with the same {{param|Priority}}. The
            mechanism is defined in {{bibref|RFC2782}}. A value
            of -1 indicates that the implementation of this
            parameter is specific to the Vendor.";
            type int64 {
              range "-1..65535";
            }
          }
          leaf ServerAddress {
            config true;
            description
            "If the value of this Parameter is a FQDN that
            resolves to multiple addresses then each address
            SHOULD be attemtped (in an implemnetation-specific
            order) until a connection can be made or all
            addresses are exhausted, in which case the next
            {{object}} instance (based on {{param|Priority}}
            and {{param|Weight}}) SHOULD be used.";
            type string {
              length "0..256";
            }
          }
          leaf Port {
            config true;
            description
            "Port number of the XMPP server for this
            {{object|##.Connection}}.";
            type uint32 {
              range "0..65535";
            }
          }
        }
        container Stats {
          description
          "XMPP Connection statistics information for this
          resource.";
          leaf ReceivedMessages {
            config false;
            description
            "The number of XMPP stanzas (iq, presence, or
            message) that have been received on this
            {{object|##.Connection}}.";
            type uint32;
            default "0";
          }
          leaf TransmittedMessages {
            config false;
            description
            "The number of XMPP stanzas (iq, presence, or
            message) that have been transmitted by this
            {{object|##.Connection}}.";
            type uint32;
            default "0";
          }
          leaf ReceivedErrorMessages {
            config false;
            description
            "The number of XMPP stanzas (iq, presence, or
            message) that have been received on this
            {{object|##.Connection}} where the type attribute
            had a value of \"error\".";
            type uint32;
            default "0";
          }
          leaf TransmittedErrorMessages {
            config false;
            description
            "The number of XMPP stanzas (iq, presence, or
            message) that have been transmitted by this
            {{object|##.Connection}} where the type attribute
            had a value of \"error\".";
            type uint32;
            default "0";
          }
        }
      }
    }
    container IEEE1905 {
      description
      "This object represents the management functions for the
      1905 capabilities as defined in {{bibref|IEEE1905.1a}}.";
      leaf Version {
        config false;
        description
        "1905 profile version number of the AL as would be sent
        in a Higher Layer response message as defined in
        {{bibref|IEEE1905.1a|Table 6-37: 1905 profile version
        TLV}}.";
        type enumeration {
          enum "1905.1";
          enum "1905.1a";
        }
      }
      container AL {
        description
        "This object represents the management functions for the
        1905 Abstraction Layer as defined in
        {{bibref|IEEE1905.1a|Section 4.4 Abstraction Layer}}.";
        leaf IEEE1905Id {
          config false;
          description
          "1905 AL MAC Address.";
          type yang:mac-address;
        }
        leaf Status {
          config false;
          description
          "The {{enum|Error}} value MAY be used by the CPE to
          indicate a locally defined error condition.";
          type enumeration {
            enum "Disabled";
            enum "Enabled";
            enum "Error_Misconfigured";
            enum "Up" {
              description
              "NOT RECOMMENDED for use; if used it  means
              {{enum|Enabled}}";
            }
            enum "Down" {
              description
              "NOT RECOMMENDED for use; if used it  means
              {{enum|Disabled}}";
            }
            enum "Unknown" {
              description
              "NOT RECOMMENDED for use; if used it  means
              {{enum|Error}}";
            }
            enum "Dormant" {
              description
              "NOT RECOMMENDED for use; if used it  means
              {{enum|Error}}";
            }
            enum "NotPresent" {
              description
              "NOT RECOMMENDED for use; if used it  means
              {{enum|Error}}";
            }
            enum "LowerLayerDown" {
              description
              "NOT RECOMMENDED for use; if used it  means
              {{enum|Error}}";
            }
            enum "Error";
          }
        }
        leaf LastChange {
          config false;
          description
          "This parameter is NOT RECOMMENDED to be used because
          IEEE1905 is not an interface.  The accumulated time
          in {{units}} since the 1905 Abstraction Layer entered
          its current operational state.";
          type uint32;
        }
        leaf-list LowerLayers {
          config false;
          description
          "This parameter is NOT RECOMMENDED to be used because
          IEEE1905 is not an interface.  {{list}} {{reference}}
          See {{bibref|TR-181i2|Section 4.2.1}}.";
          type string;
        }
        leaf-list RegistrarFreqBand {
          config false;
          description
          "{{list}} See {{bibref|IEEE1905.1a|Table 6-25:
          SupportedFreqBand TLV}}. {{enum}}";
          type enumeration {
            enum "802.11 2.4 GHz";
            enum "802.11 5 GHz";
            enum "802.11 60 GHz";
          }
        }
        leaf InterfaceNumberOfEntries {
          config false;
          description
          "{{numentries}}";
          type uint32;
        }
        list Interface {
          key "InterfaceId";
          config true;
          description
          "The 1905 interface table (described in
          {{bibref|IEEE1905.1a|sub-clause 5 Abstraction Layer
          Management}}).";
          leaf InterfaceId {
            config true;
            description
            "MAC Address of this interface.  This is the value
            of the intfAddress parameter defined in
            {{bibref|IEEE1905.1a|Table 5-2: intfDescriptor
            elements}}";
            type yang:mac-address;
          }
          leaf Status {
            config false;
            description
            "This parameter is based on ''ifOperStatus'' from
            {{bibref|RFC2863}}.";
            type enumeration {
              enum "Up";
              enum "Down";
              enum "Unknown";
              enum "Dormant";
              enum "NotPresent";
              enum "LowerLayerDown";
              enum "Error";
            }
          }
          leaf LastChange {
            config false;
            description
            "This parameter is NOT RECOMMENDED to be used
            because it is not a parameter defined in a 1905
            ALME primitive or protocol TLV.  The accumulated
            time in {{units}} since the interface entered its
            current operational state.";
            type uint32;
          }
          leaf-list LowerLayers {
            config false;
            description
            "This parameter is NOT RECOMMENDED to be used
            because it is not a parameter defined in a 1905
            ALME primitive or protocol TLV.  {{list}}
            {{reference|an interface object that is stacked
            immediately below this interface object}}  See
            {{bibref|TR-181i2|Section 4.2.1}}.";
            type string;
          }
          leaf InterfaceStackReference {
            config false;
            description
            "Path name of an interface object described by this
            1905 {{object}}. Referenced interface object MUST
            have a MACAddress and the InterfaceId MUST be the
            same as the interface object MACAddress.";
            type string {
              length "0..256";
            }
          }
          leaf MediaType {
            config false;
            description
            "Media type of this {{object}}. This is derived from
            the value of the intfType parameter defined in
            {{bibref|IEEE1905.1a|Tables 5.2: intfDescriptor
            elements}}. {{enum}}";
            type enumeration {
              enum "IEEE 802.3u" {
                description
                "IEEE 802.3u Fast Ethernet";
              }
              enum "IEEE 802.3ab" {
                description
                "IEEE 802.3ab Gigabit Ethernet";
              }
              enum "IEEE 802.11b" {
                description
                "IEEE 802.11b (2.4GHz)";
              }
              enum "IEEE 802.11g" {
                description
                "IEEE 802.11g (2.4GHz)";
              }
              enum "IEEE 802.11a" {
                description
                "IEEE 802.11a (5GHz)";
              }
              enum "IEEE 802.11n 2.4" {
                description
                "IEEE 802.11n (2.4GHz)";
              }
              enum "IEEE 802.11n 5.0" {
                description
                "IEEE 802.11n (5GHz)";
              }
              enum "IEEE 802.11ac" {
                description
                "IEEE 802.11ac (5GHz)";
              }
              enum "IEEE 802.11ad" {
                description
                "IEEE 802.11ad (60GHz)";
              }
              enum "IEEE 802.11af" {
                description
                "IEEE 802.11af";
              }
              enum "IEEE 1901 Wavelet" {
                description
                "IEEE 1901 Wavelet";
              }
              enum "IEEE 1901 FFT" {
                description
                "IEEE 1901 FFT";
              }
              enum "MoCAv1.1" {
                description
                "MoCAv1.1";
              }
              enum "Generic PHY";
            }
          }
          leaf GenericPhyOUI {
            config false;
            description
            "OUI of the Generic Phy networking technology of the
            local interface that would be included in a Generic
            Phy Device Information Type TLV defined in
            {{bibref|IEEE1905.1a|Tables 6-29: Generic Phy
            Device Information type TLV}}.";
            type string {
              length "6";
              pattern "[0-9A-F]{6}";
            }
          }
          leaf GenericPhyVariant {
            config false;
            description
            "Variant Index of the Generic Phy networking
            technology of the local interface that would be
            included in a Generic Phy Device Information Type
            TLV defined in {{bibref|IEEE1905.1a|Tables 6-29:
            Generic Phy Device Information type TLV}}.";
            type yang:hex-string {
              length "1";
            }
          }
          leaf GenericPhyURL {
            config false;
            description
            "URL to Generic Phy XML Description of the Generic
            Phy networking technology of the local interface
            that would be included in a Generic Phy Device
            Information Type TLV defined in
            {{bibref|IEEE1905.1a|Table 6-29: Generic Phy device
            information type TLV}}.";
            type string {
              length "0..1024";
            }
          }
          leaf SetIntfPowerStateEnabled {
            config true;
            description
            "Enables or disables the Abstraction Layer's ability
            to set the power state for the interface.  Boolean
            can be {{true}} for \"enabled\" and {{false}} for
            \"disabled\".";
            type boolean;
          }
          leaf PowerState {
            config true;
            description
            "The Power State of this {{object}}. This is derived
            from the value of the powerState parameter as
            defined in {{bibref|IEEE1905.1a|Tables 5.3:
            ALME-SET-INTF-PWR-STATE.request parameters and
            Table 5.7: ALME-GET-INTF-PWR-STATE.response
            parameters}}. {{enum}}";
            type enumeration {
              enum "On";
              enum "Power_Save" {
                description
                "not used when written";
              }
              enum "Off";
              enum "Unsupported" {
                description
                "not used when written";
              }
            }
          }
          leaf VendorPropertiesNumberOfEntries {
            config false;
            description
            "{{numentries}}";
            type uint32;
          }
          leaf LinkNumberOfEntries {
            config false;
            description
            "{{numentries}}";
            type uint32;
          }
          list VendorProperties {
            key "_id";
            leaf "_id" {
              type "uint32";
            }
            config false;
            description
            "This object defines the vendor specific properties
            (vendorSpecificInfo field) of this
            {{object|##.Interface}} as defined in
            {{bibref|IEEE1905.1a|Table 5-2: intfDescriptor
            elements}}.";
            leaf OUI {
              config false;
              description
              "Organizationally unique identifier of a
              manufacturer of this {{object|##.Interface}}.
              Represented as a six hexadecimal-digit value
              using all upper-case letters and including any
              leading zeros according to
              {{bibref|IEEE1905.1a|Table 5-20:
              VendorSpecificInfo information element}}.
              {{pattern}}";
              type string {
                length "6";
                pattern "[0-9A-F]{6}";
              }
            }
            leaf Information {
              config false;
              description
              "A hexbinary string used to to provide vendor
              specific information about this
              {{object|##.Interface}}. This is the value of the
              vendorSpecificInfo parameter defined in
              {{bibref|IEEE1905.1a|Table 5-20:
              VendorSpecificInfo information element}}.";
              type yang:hex-string {
                length "0..65535";
              }
            }
          }
          list Link {
            key "InterfaceId IEEE1905Id";
            config false;
            description
            "This object defines the 1905 neighbors and link
            properties.";
            leaf InterfaceId {
              config false;
              description
              "MAC Address of the interface of the Neighbor for
              this {{object}}. This value comes from the
              neighbor’s Topology discovery message as defined
              in {{bibref|IEEE1905.1a|Table 6-9: MAC address
              typeTLV}}.";
              type yang:mac-address;
            }
            leaf IEEE1905Id {
              config false;
              description
              "MAC Address of the 1905 AL entity of the Neighbor
              device on this {{object}}. This value comes from
              the neighbor’s Topology discovery message as
              defined in {{bibref|IEEE1905.1a|Table 6-8: AL MAC
              address type TLV}}.";
              type yang:mac-address;
            }
            leaf MediaType {
              config false;
              description
              "Media type of this {{object}}. This value is
              derived from the neighbor’s Topology response
              message 1905 device information type TLV Media
              Type field as defined in
              {{bibref|IEEE1905.1a|Table 6-12: Media type}}.
              {{enum}}";
              type enumeration {
                enum "IEEE 802.3u" {
                  description
                  "IEEE 802.3u Fast Ethernet";
                }
                enum "IEEE 802.3ab" {
                  description
                  "IEEE 802.3ab Gigabit Ethernet";
                }
                enum "IEEE 802.11b" {
                  description
                  "IEEE 802.11b (2.4GHz)";
                }
                enum "IEEE 802.11g" {
                  description
                  "IEEE 802.11g (2.4GHz)";
                }
                enum "IEEE 802.11a" {
                  description
                  "IEEE 802.11a (5GHz)";
                }
                enum "IEEE 802.11n 2.4" {
                  description
                  "IEEE 802.11n (2.4GHz)";
                }
                enum "IEEE 802.11n 5.0" {
                  description
                  "IEEE 802.11n (5GHz)";
                }
                enum "IEEE 802.11ac" {
                  description
                  "IEEE 802.11ac (5GHz)";
                }
                enum "IEEE 802.11ad" {
                  description
                  "IEEE 802.11ad (60GHz)";
                }
                enum "IEEE 802.11af" {
                  description
                  "IEEE 802.11af";
                }
                enum "IEEE 1901 Wavelet" {
                  description
                  "IEEE 1901 Wavelet";
                }
                enum "IEEE 1901 FFT" {
                  description
                  "IEEE 1901 FFT";
                }
                enum "MoCAv1.1" {
                  description
                  "MoCAv1.1";
                }
                enum "Generic PHY";
              }
            }
            leaf GenericPhyOUI {
              config false;
              description
              "OUI of the Generic Phy networking technology of
              the interface of the Neighbor for this
              {{object|#.Link}}. This value is from a Generic
              Phy response message field as defined in
              {{bibref|IEEE1905.1a|Tables 6-29: Generic Phy
              Device Information type TLV}}.";
              type string {
                length "6";
                pattern "[0-9A-F]{6}";
              }
            }
            leaf GenericPhyVariant {
              config false;
              description
              "Variant Index of the Generic Phy networking
              technology of the interface of the Neighbor for
              this {{object|#.Link}}. This value is from a
              Generic Phy response message variant index field
              as defined in {{bibref|IEEE1905.1a|Tables 6-29:
              Generic Phy Device Information type TLV}}.";
              type yang:hex-string {
                length "1";
              }
            }
            leaf GenericPhyURL {
              config false;
              description
              "URL to Generic Phy XML Description of the Generic
              Phy networking technology of the interface of the
              Neighbor for this {{object|#.Link}}. This value
              is from a Generic Phy response message URL to
              Generic Phy field as defined in
              {{bibref|IEEE1905.1a|Table 6-29: Generic Phy
              device information type TLV}}.";
              type string {
                length "0..1024";
              }
            }
            container Metric {
              description
              "This object represents the metrics for this
              {{object|##.Link}} as defined in
              {{bibref|IEEE1905.1a|Tables 6-18: 1905
              transmitter link metrics and Table 6-20: 1905
              receiver link metrics}}.";
              leaf IEEE802dot1Bridge {
                config false;
                description
                "Indicates whether or not the 1905 link includes
                one or more IEEE 802.1 bridges.  If {{false}},
                the 1905 link does not include an IEEE 802.1
                bridge.  If {{true}}, the 1905 link does
                include one or more IEEE 802.1 bridges.";
                type boolean;
              }
              leaf PacketErrors {
                config false;
                description
                "Estimated number of lost {{units}} on the
                transmit side of the link
                {{bibref|IEEE1905.1a|Table 6-18: 1905
                transmitter link metrics}} during a measurement
                period.";
                type yang:counter32;
              }
              leaf PacketErrorsReceived {
                config false;
                description
                "Estimated number of lost {{units}} on the
                receive side of the link
                {{bibref|IEEE1905.1a|Table 6-20: 1905 receiver
                link metrics}} during a measurement period.";
                type yang:counter32;
              }
              leaf TransmittedPackets {
                config false;
                description
                "Estimated number of {{units}} sent to the
                Neighbor on this {{object|##.Link}}, in the
                same measurement period used to estimate
                {{param|PacketErrors}}.";
                type yang:counter32;
              }
              leaf PacketsReceived {
                config false;
                description
                "Estimated number of {{units}} received from
                this Neighbor on this {{object|##.Link}}
                {{bibref|IEEE1905.1a|Table 6-20: 1905 receiver
                link metrics}}, in the same measurement period
                used to estimate {{param|PacketErrors}}.";
                type yang:counter32;
              }
              leaf MACThroughputCapacity {
                config false;
                description
                "The maximum MAC throughput in {{units}} between
                this {{object|###.Interface}} and the Neighbor
                on this {{object|##.Link}} that is estimated at
                this {{object|###.Interface}}.";
                type uint32;
              }
              leaf LinkAvailability {
                config false;
                description
                "The estimated average {{units}} of time that
                the {{object|##.Link}} is available for data
                transmissions.";
                type uint32 {
                  range "0..100";
                }
              }
              leaf PHYRate {
                config false;
                description
                "The Physical Layer (PHY) rate in {{units}}
                between this {{object|###.Interface}} and the
                Neighbor on this {{object|##.Link}} that is
                estimated at this {{object|###.Interface}}.";
                type uint32;
              }
              leaf RSSI {
                config false;
                description
                "The estimated Received Signal Strength
                Indicator (RSSI) ratio in {{units}} between
                this {{object|###.Interface}} and the Neighbor
                on this {{object|##.Link}} that is estimated at
                the receive side of this
                {{object|###.Interface}}.";
                type uint32 {
                  range "0..255";
                }
              }
            }
          }
        }
        container ForwardingTable {
          description
          "This object represents the rules to forward PDUs
          between interfaces within the 1905 Abstraction Layer.";
          leaf SetForwardingEnabled {
            config true;
            description
            "Abstraction Layer ability to set, modify, and
            remove {{object|ForwardingRule}} entries for
            interfaces.  Boolean can be {{true}} for
            \"enabled\" and {{false}} for \"disabled\".";
            type boolean;
          }
          leaf ForwardingRuleNumberOfEntries {
            config false;
            description
            "{{numentries}}";
            type uint32;
          }
          list ForwardingRule {
            key "_id";
            leaf "_id" {
              type "uint32";
            }
            config true;
            description
            "The 1905 fowarding rule for the
            ALME-SET-FWD-RULE.request and
            ALME-GET-FWD-RULES.response with classification
            criteria as defined in {{bibref|IEEE1905.1a|Table
            5-9: ClassificationSet elements}}.";
            leaf-list InterfaceList {
              config true;
              description
              "The list of interfaces to which a frame
              satisfying the following classification criteria
              should be forwarded (intfAddressList parameter as
              defined in {{bibref|IEEE1905.1a|Table 5-8:
              ALME-SET-FWD-RULE.request parameters and Table
              5-12: fwdRuleList elements}}). {{list}} Each list
              item MUST be the path name of an object, which
              MUST be a row of an {{object|##.Interface}}
              object.  If the referenced item is deleted, the
              corresponding item MUST be removed from the list.
              {{noreference}}";
              type string {
                length "0..256";
              }
            }
            leaf MACDestinationAddress {
              config true;
              description
              "The destination MAC address.";
              type yang:mac-address;
            }
            leaf MACDestinationAddressFlag {
              config true;
              description
              "If {{false}}, the classification criterion
              {{param|MACDestinationAddress}} is ignored.  If
              {{true}}, the classification criterion
              {{param|MACDestinationAddress}} is used.";
              type boolean;
              default "false";
            }
            leaf MACSourceAddress {
              config true;
              description
              "The source MAC address.";
              type yang:mac-address;
            }
            leaf MACSourceAddressFlag {
              config true;
              description
              "If {{false}}, the classification criterion
              {{param|MACSourceAddress}} is ignored.  If
              {{true}}, the classification criterion
              {{param|MACSourceAddress}} is used.";
              type boolean;
              default "false";
            }
            leaf EtherType {
              config true;
              description
              "Ether Type Field in a frame.";
              type uint32;
            }
            leaf EtherTypeFlag {
              config true;
              description
              "If {{false}}, the classification criterion
              {{param|EtherType}} is ignored.  If {{true}}, the
              classification {{param|EtherType}} is used.";
              type boolean;
              default "false";
            }
            leaf Vid {
              config true;
              description
              "IEEE 802.1Q VLAN ID in a frame.";
              type uint32 {
                range "0..4095";
              }
            }
            leaf VidFlag {
              config true;
              description
              "If {{false}}, the classification criterion
              {{param|Vid}} is ignored.  If {{true}}, the
              classification {{param|Vid}} is used.";
              type boolean;
              default "false";
            }
            leaf PCP {
              config true;
              description
              "IEEE 802.1Q Priority Code Point field.";
              type uint32 {
                range "0..7";
              }
            }
            leaf PCPFlag {
              config true;
              description
              "If {{false}}, the classification criterion
              {{param|PCP}} is ignored.  If {{true}}, the
              classification {{param|PCP}} is used.";
              type boolean;
              default "false";
            }
          }
        }
        container NetworkTopology {
          description
          "This object represents the 1905 Network Topology
          capabilities of this device.";
          leaf Enable {
            config true;
            description
            "Enables or disables the 1905 Network Topology
            reporting (via TR-069). When {{true}}, the device
            clears and (re)populates the
            {{object|IEEE1905Device}} and {{object|ChangeLog}}
            tables.  When {{false}}, the contents of the
            {{object|IEEE1905Device}} and {{object|ChangeLog}}
            tables have no meaning.";
            type boolean;
          }
          leaf Status {
            config false;
            description
            "{{enum}}";
            type enumeration {
              enum "Incomplete" {
                description
                "Indicates that the device is populating the
                topology object during the transient phase.";
              }
              enum "Available" {
                description
                "Indicates that the transient phase is over and
                the device is maintaining and updating the
                topology object as changes occur.";
              }
              enum "Error_Misconfigured" {
                description
                "NOT RECOMMENDED for use; if used, indicates
                that a necessary configuration value is
                undefined or invalid.";
              }
            }
          }
          leaf MaxChangeLogEntries {
            config true;
            description
            "The maximum number of entries allowed in the
            {{object|ChangeLog}} table.";
            type uint32 {
              range "1..max";
            }
          }
          leaf LastChange {
            config false;
            description
            "{{reference}} If the {{object|ChangeLog}} is
            modified the parameter is modified to reflect the
            last entry added to the {{object|ChangeLog}}.";
            type string {
              length "0..256";
            }
          }
          leaf IEEE1905DeviceNumberOfEntries {
            config false;
            description
            "{{numentries}}";
            type uint32;
          }
          leaf ChangeLogNumberOfEntries {
            config false;
            description
            "{{numentries}}";
            type uint32;
          }
          list ChangeLog {
            key "_id";
            leaf "_id" {
              type "uint32";
            }
            config false;
            description
            "This object represents log entries for changes in
            the 1905 Network Topology.  The Change Log is a
            First In First Out queue where the oldest entries
            (defined by values of the {{param|TimeStamp}}
            parameter) are deleted once the log is full.";
            leaf TimeStamp {
              config false;
              description
              "Date and Time at which the entry was added to the
              {{object}} table.";
              type yang:date-and-time;
            }
            leaf EventType {
              config false;
              description
              "Type of event for this entry.  {{enum}}";
              type enumeration {
                enum "NewNeighbor" {
                  description
                  "Entry represents a discovery of a Neighbor.";
                }
                enum "LostNeighbor" {
                  description
                  "Entry represents the loss of a Neighbor.";
                }
              }
            }
            leaf ReporterDeviceId {
              config false;
              description
              "1905 AL MAC Address of device which reported the
              change.";
              type yang:mac-address;
            }
            leaf ReporterInterfaceId {
              config false;
              description
              "MAC Address of the interface of the reporting
              device on which the change has been detected.";
              type yang:mac-address;
            }
            leaf NeighborType {
              config false;
              description
              "Type of Neighbor for this event.  {{enum}}";
              type enumeration {
                enum "IEEE1905";
                enum "Non-IEEE1905";
              }
            }
            leaf NeighborId {
              config false;
              description
              "If value of the {{param|NeighborType}} parameter
              is {{enum|IEEE1905|NeighborType}}, then the value
              of this parameter is the 1905 AL MAC Address of
              the Neighbor.";
              type yang:mac-address;
            }
          }
          list IEEE1905Device {
            key "IEEE1905Id";
            config false;
            description
            "This object represents an instance of discovered
            1905 Devices in the network (received Topology
            discovery message as defined in
            {{bibref|IEEE1905.1a|Clause 6.3.1}}).";
            leaf IEEE1905Id {
              config false;
              description
              "1905 AL MAC Address.";
              type yang:mac-address;
            }
            leaf Version {
              config false;
              description
              "1905 profile version number in Higher Layer
              Response message as defined in
              {{bibref|IEEE1905.1a|Table 6-37: 1905 profile
              version TLV}}.";
              type enumeration {
                enum "1905.1";
                enum "1905.1a";
              }
            }
            leaf-list RegistrarFreqBand {
              config false;
              description
              "{{list}} of frequency bands identified as
              supported for a registrar role in an
              AP-autoconfiguration response message as defined
              in {{bibref|IEEE1905.1a|Table 6-25:
              SupportedFreqBand TLV}} {{enum}}.";
              type enumeration {
                enum "802.11 2.4 GHz";
                enum "802.11 5 GHz";
                enum "802.11 60 GHz";
              }
            }
            leaf FriendlyName {
              config false;
              description
              "Friendly Name String received in Higher Layer
              response message as defined in
              {{bibref|IEEE1905.1a|Table 6-30: Device
              Identification Type TLV}}.";
              type string {
                length "0..128";
              }
            }
            leaf ManufacturerName {
              config false;
              description
              "Manufacturer Name String received in Higher Layer
              response message as defined in
              {{bibref|IEEE1905.1a|Table 6-30: Device
              Identification Type TLV}}.";
              type string {
                length "0..128";
              }
            }
            leaf ManufacturerModel {
              config false;
              description
              "Manufacturer Model String received in Higher
              Layer response message as defined in
              {{bibref|IEEE1905.1a|Table 6-30: Device
              Identification Type TLV}}.";
              type string {
                length "0..128";
              }
            }
            leaf ControlURL {
              config false;
              description
              "Control URL received in Higher Layer response
              message as defined in defined in
              {{bibref|IEEE1905.1a|Table 6-31: Control URL Type
              TLV}}.";
              type string {
                length "0..1024";
              }
            }
            leaf VendorPropertiesNumberOfEntries {
              config false;
              description
              "{{numentries}}";
              type uint32;
            }
            leaf IPv4AddressNumberOfEntries {
              config false;
              description
              "{{numentries}}";
              type uint32;
            }
            leaf IPv6AddressNumberOfEntries {
              config false;
              description
              "{{numentries}}";
              type uint32;
            }
            leaf InterfaceNumberOfEntries {
              config false;
              description
              "{{numentries}}";
              type uint32;
            }
            leaf NonIEEE1905NeighborNumberOfEntries {
              config false;
              description
              "{{numentries}}";
              type uint32;
            }
            leaf IEEE1905NeighborNumberOfEntries {
              config false;
              description
              "{{numentries}}";
              type uint32;
            }
            leaf L2NeighborNumberOfEntries {
              config false;
              description
              "{{numentries}}";
              type uint32;
            }
            leaf BridgingTupleNumberOfEntries {
              config false;
              description
              "{{numentries}}";
              type uint32;
            }
            list IPv4Address {
              key "MACAddress IPv4Address";
              config false;
              description
              "This object represents represents all IPv4
              addresses reported for a MAC address (AL or
              interface) in a Higher Layer response message for
              the IEEE1905Device as defined in
              {{bibref|IEEE1905.1a|Table 6-32: IPv4 type TLV}}.";
              leaf MACAddress {
                config false;
                description
                "MAC Address.";
                type yang:mac-address;
              }
              leaf IPv4Address {
                config false;
                description
                "IPv4 Address.";
                type inet:ipv4-address;
              }
              leaf IPv4AddressType {
                config false;
                description
                "The IPv4 Address Type of this
                {{param|IPv4Address}}. {{enum}}";
                type enumeration {
                  enum "Unknown";
                  enum "DHCP";
                  enum "Static";
                  enum "Auto-IP";
                }
              }
              leaf DHCPServer {
                config false;
                description
                "Either IPv4 address of DHCPv4 server or IPv6
                address of DHCPv6 server.";
                type inet:ip-address;
              }
            }
            list IPv6Address {
              key "MACAddress IPv6Address";
              config false;
              description
              "This object represents represents all IPv6
              addresses reported for a MAC address (AL or
              interface) in a Higher Layer response message for
              the IEEE1905Device as defined in
              {{bibref|IEEE1905.1a|Table 6-34: IPv6 type TLV}}.";
              leaf MACAddress {
                config false;
                description
                "MAC Address.";
                type yang:mac-address;
              }
              leaf IPv6Address {
                config false;
                description
                "IPv6 Address.";
                type inet:ipv6-address;
              }
              leaf IPv6AddressType {
                config false;
                description
                "The IPv6 Address Type of this
                {{param|IPv6Address}}. {{enum}}";
                type enumeration {
                  enum "Unknown";
                  enum "LinkLocal";
                  enum "DHCP";
                  enum "Static";
                  enum "SLAAC";
                }
              }
              leaf IPv6AddressOrigin {
                config false;
                description
                "\"::\" or the IPv6 address of the origin of
                this IPv6 address.";
                type inet:ipv6-address;
              }
            }
            list VendorProperties {
              key "_id";
              leaf "_id" {
                type "uint32";
              }
              config false;
              description
              "This object represents vendor specific
              information received in a message with a Vendor
              specific TLV (as defined in in
              {{bibref|IEEE1905.1a|Table 6-7: Vendor specific
              TLV}}).";
              leaf MessageType {
                config false;
                description
                "The Message type of a message received from
                this IEEE1905Device that contained a Vendor
                specific TLV, as defined in
                {{bibref|IEEE1905.1a|Table 6-4: Message type}}.";
                type yang:hex-string {
                  length "1";
                }
              }
              leaf OUI {
                config false;
                description
                "This is the value of the Vendor specific OUI
                defined in {{bibref|IEEE1905.1a|Table 6-7:
                Vendor specific TLV}}.  {{pattern}}";
                type string {
                  length "6";
                  pattern "[0-9A-F]{6}";
                }
              }
              leaf Information {
                config false;
                description
                "A hexbinary string used to provide vendor
                specific information.  This is the value of the
                Vendor specific information parameter defined
                in {{bibref|IEEE1905.1a|Table 6-7: Vendor
                specific TLV}}.";
                type yang:hex-string {
                  length "0..65535";
                }
              }
            }
            list Interface {
              key "InterfaceId";
              config false;
              description
              "This object represents an instance of an
              interface for the {{object|##.IEEE1905Device}}.";
              leaf InterfaceId {
                config false;
                description
                "MAC Address of the interface.  This comes from
                the Topology response message as defined in
                {{bibref|IEEE1905.1a|Table 6-10: 1905 device
                information type TLV}}.";
                type yang:mac-address;
              }
              leaf MediaType {
                config false;
                description
                "Media type of this {{object}}. This comes from
                the Topology response message as defined in
                {{bibref|IEEE1905.1a|Table 6-10: 1905 device
                information type TLV}}. {{enum}}";
                type enumeration {
                  enum "IEEE 802.3u" {
                    description
                    "IEEE 802.3u Fast Ethernet";
                  }
                  enum "IEEE 802.3ab" {
                    description
                    "IEEE 802.3ab Gigabit Ethernet";
                  }
                  enum "IEEE 802.11b" {
                    description
                    "IEEE 802.11b (2.4GHz)";
                  }
                  enum "IEEE 802.11g" {
                    description
                    "IEEE 802.11g (2.4GHz)";
                  }
                  enum "IEEE 802.11a" {
                    description
                    "IEEE 802.11a (5GHz)";
                  }
                  enum "IEEE 802.11n 2.4" {
                    description
                    "IEEE 802.11n (2.4GHz)";
                  }
                  enum "IEEE 802.11n 5.0" {
                    description
                    "IEEE 802.11n (5GHz)";
                  }
                  enum "IEEE 802.11ac" {
                    description
                    "IEEE 802.11ac (5GHz)";
                  }
                  enum "IEEE 802.11ad" {
                    description
                    "IEEE 802.11ad (60GHz)";
                  }
                  enum "IEEE 802.11af" {
                    description
                    "IEEE 802.11af";
                  }
                  enum "IEEE 1901 Wavelet" {
                    description
                    "IEEE 1901 Wavelet";
                  }
                  enum "IEEE 1901 FFT" {
                    description
                    "IEEE 1901 FFT";
                  }
                  enum "MoCAv1.1" {
                    description
                    "MoCAv1.1";
                  }
                  enum "Generic PHY";
                }
              }
              leaf PowerState {
                config false;
                description
                "The Power State of this {{object}}.
                \"{{enum|Off}}\" is used for interfaces
                identified in a Power Off Interface TLV as
                defined in {{bibref|IEEE1905.1a|Table 6-38}}.
                \"{{enum|On}}\" is used for all other
                interfaces.  \"{{enum|Power_Save}}\" and
                \"{{enum|Unsupported}}\" are not used at this
                time.  Updated as a result of a received
                Interface Power Change response with “request
                completed” or “alternate change made” Interface
                Power Change status as defined in
                {{bibref|IEEE1905.1a|Table 6-40: Interface
                Power Change status TLV}}. {{enum}}";
                type enumeration {
                  enum "On";
                  enum "Power_Save";
                  enum "Off";
                  enum "Unsupported";
                }
              }
              leaf GenericPhyOUI {
                config false;
                description
                "{{param}} of this {{object|#.Interface}}.
                {{pattern}}";
                type string {
                  length "6";
                  pattern "[0-9A-F]{6}";
                }
              }
              leaf GenericPhyVariant {
                config false;
                description
                "Variant Index of the Generic Phy networking
                technology of this {{object|#.Interface}}. This
                value is from a Generic Phy response message
                variant index field as defined in
                {{bibref|IEEE1905.1a|Table 6-29: Generic Phy
                device information type TLV}}.";
                type yang:hex-string {
                  length "1";
                }
              }
              leaf GenericPhyURL {
                config false;
                description
                "URL to Generic Phy XML Description of the
                Generic Phy networking technology of this
                {{object|#.Interface}}. This value is from a
                Generic Phy response message URL to generic phy
                field as defined in {{bibref|IEEE1905.1a|Table
                6-29: Generic Phy device information type
                TLV}}.";
                type string {
                  length "0..1024";
                }
              }
              leaf NetworkMembership {
                config false;
                description
                "MACAddress Field from Media specific
                information for an 802.11 interface provided in
                a Topology response message 1905 device
                information type TLV as defined in
                {{bibref|IEEE1905.1a|Table 6-13: IEEE 802.11
                specific information}}.";
                type yang:mac-address;
              }
              leaf Role {
                config false;
                description
                "Field from Media specific information for an
                802.11 interface provided in a Topology
                response message 1905 device information type
                TLV as defined in {{bibref|IEEE1905.1a|Table
                6-13: IEEE 802.11 specific information}}.
                {{enum}}";
                type enumeration {
                  enum "AP";
                  enum "non-AP/non-PCP STA";
                  enum "Wi-Fi P2P Client";
                  enum "Wi-Fi P2P Group Owner";
                  enum "802.11adPCP";
                }
              }
              leaf APChannelBand {
                config false;
                description
                "Hexadecimal digit.  Field from Media specific
                information for an 802.11 interface provided in
                a Topology response message 1905 device
                information type TLV as defined in
                {{bibref|IEEE1905.1a|Table 6-13: IEEE 802.11
                specific information}}";
                type yang:hex-string {
                  length "1";
                }
              }
              leaf FrequencyIndex1 {
                config false;
                description
                "Field from Media specific information for an
                802.11 interface provided in a Topology
                response message 1905 device information type
                TLV as defined in {{bibref|IEEE1905.1a|Table
                6-13: IEEE 802.11 specific information}}";
                type yang:hex-string {
                  length "1";
                }
              }
              leaf FrequencyIndex2 {
                config false;
                description
                "Field from Media specific information for an
                802.11 interface provided in a Topology
                response message 1905 device information type
                TLV as defined in {{bibref|IEEE1905.1a|Table
                6-13: IEEE 802.11 specific information}}";
                type yang:hex-string {
                  length "1";
                }
              }
            }
            list NonIEEE1905Neighbor {
              key "LocalInterface NeighborInterfaceId";
              config false;
              description
              "This object represents an instance of a
              Non-IEEE1905 Neighbor for the
              {{object|##.IEEE1905Device}}. These fields come
              from a Topology response message as defined in
              {{bibref|IEEE1905.1a|Table 6-14: Non-1905
              neighbor device TLV}}.";
              leaf LocalInterface {
                config false;
                description
                "{{reference}}";
                type string {
                  length "0..256";
                }
              }
              leaf NeighborInterfaceId {
                config false;
                description
                "MAC Address of the interface for the
                {{object}}.";
                type yang:mac-address;
              }
            }
            list L2Neighbor {
              key "LocalInterface NeighborInterfaceId";
              config false;
              description
              "This object represents an instance of an L2
              Neighbor for the {{object|##.IEEE1905Device}}.
              These fields come from a Topology response
              message as defined in {{bibref|IEEE1905.1a|Table
              6-41: L2 neighbor device TLV}}.";
              leaf LocalInterface {
                config false;
                description
                "{{reference}}";
                type string {
                  length "0..256";
                }
              }
              leaf NeighborInterfaceId {
                config false;
                description
                "MAC Address of the {{object}}.";
                type yang:mac-address;
              }
              leaf-list BehindInterfaceIds {
                config false;
                description
                "{{list}} Behind MAC Addresses of the
                {{object}}.";
                type yang:mac-address;
              }
            }
            list IEEE1905Neighbor {
              key "LocalInterface NeighborDeviceId";
              config false;
              description
              "This object represents an instance of an
              {{object}} for the {{object|##.IEEE1905Device}}.
              These values are from the Topology response
              message as defined in {{bibref|IEEE1905.1a|Table
              6-15: 1905 neighbor device TLV}}.";
              leaf LocalInterface {
                config false;
                description
                "{{reference}}";
                type string {
                  length "0..256";
                }
              }
              leaf NeighborDeviceId {
                config false;
                description
                "1905 AL MAC Address of the Neighbor.";
                type yang:mac-address;
              }
              leaf MetricNumberOfEntries {
                config false;
                description
                "{{numentries}}";
                type uint32;
              }
            }
            list BridgingTuple {
              key "_id";
              leaf "_id" {
                type "uint32";
              }
              config false;
              description
              "This object represents an instance of an
              {{object}} for the {{object|##.IEEE1905Device}}.
              These values come from the 1905 Device’s Topology
              response message as defined in
              {{bibref|IEEE1905.1a|Table 6-11: Device bridging
              capability TLV}}.";
              leaf-list InterfaceList {
                config false;
                description
                "{{list}} {{reference}}";
                type string {
                  length "0..256";
                }
              }
            }
          }
        }
        container Security {
          description
          "This object represents the Security configuration for
          the 1905 device as defined in
          {{bibref|IEEE1905.1a|Section 9.2 Security Setup
          Methods}}.";
          leaf-list SetupMethod {
            config true;
            description
            "{{list}} Supported security setup method(s) for the
            network.  {{enum}}";
            type enumeration {
              enum "UCPK" {
                description
                "User Configured Passphrase or Key";
              }
              enum "PBC" {
                description
                "Push Button Configuration";
              }
              enum "NFCNK" {
                description
                "Near-field Communication Network Key";
              }
            }
          }
          leaf Password {
            config true;
            description
            "1905 network passphrase for generating security
            keys.";
            type string;
          }
        }
        container NetworkingRegistrar {
          description
          "This object represents the detected Network
          Registrars detection function for the IEEE 1905
          network.  They are determined by received
          AP-autoconfiguration response messages with Registrar
          role, with supported band as defined in
          {{bibref|IEEE1905.1a|Table 6-25: SupportedFreqBand
          TLV}}";
          leaf-list Registrar2dot4 {
            config false;
            description
            "{{list}} 1905 AL MAC addresses as determined by
            source MAC address in received AP-autoconfiguration
            response messages with supported frequency band of
            802.11 2.4 GHz.";
            type yang:mac-address;
          }
          leaf-list Registrar5 {
            config false;
            description
            "{{list}} 1905 AL MAC addresses as determined by
            source MAC address in received AP-autoconfiguration
            response messages with supported frequency band of
            802.11 5 GHz.";
            type yang:mac-address;
          }
          leaf-list Registrar60 {
            config false;
            description
            "{{list}} 1905 AL MAC addresses as determined by
            source MAC address in received AP-autoconfiguration
            response messages with supported frequency band of
            802.11 60 GHz.";
            type yang:mac-address;
          }
        }
      }
    }
    container MQTT {
      description
      "MQTT Base object describing all MQTT related parameters
      and objects {{bibref|MQTT31}},";
      leaf ClientNumberOfEntries {
        config false;
        description
        "{{numentries}}";
        type uint32;
      }
      leaf BrokerNumberOfEntries {
        config false;
        description
        "{{numentries}}";
        type uint32;
      }
      container Capabilities {
        description
        "Indicates the MQTT capabilities of the device.";
        leaf-list ProtocolVersionsSupported {
          config false;
          description
          "Indicates the supported protocol versions.  {{enum}}";
          type enumeration {
            enum "3.1" {
              description
              "Protocol according to {{bibref|MQTT31}}";
            }
            enum "3.1.1" {
              description
              "Protocol according to {{bibref|MQTT311}}";
            }
          }
        }
        leaf-list TransportProtocolSupported {
          config false;
          description
          "Indicates the supported transport protocols.
          {{enum}}";
          type enumeration {
            enum "TCP/IP";
            enum "TLS";
            enum "WebSocket";
          }
        }
        leaf MaxNumberOfClientSubscriptions {
          config false;
          description
          "Indicates the maximum number of subscriptions per
          MQTT client, which can be stored in the
          {{object|#.Client.{i}.Subscription}} table.  A value
          of 0 means no limit.";
          type uint32;
        }
        leaf MaxNumberOfBrokerBridges {
          config false;
          description
          "Indicates the maximum number of bridges, which can be
          configured in the {{object|#.Broker.{i}.Bridge}}
          table.  A value of 0 means no limit.";
          type uint32;
        }
        leaf MaxNumberOfBrokerBridgeSubscriptions {
          config false;
          description
          "Indicates the maximum number of subscriptions, which
          can be stored per bridge instance in the
          {{object|#.Broker.{i}.Bridge.{i}.Subscription}}
          table.  A value of 0 means no limit.";
          type uint32;
        }
      }
      list Client {
        key "Name";
        unique "Alias";
        config true;
        description
        "MQTT client table.  Contains a list of configured MQTT
        clients.";
        leaf Alias {
          config true;
          description
          "{{datatype|expand}}";
          type Alias;
        }
        leaf Name {
          config true;
          description
          "The textual name of the MQTT client.";
          type string {
            length "0..64";
          }
        }
        leaf Enable {
          config true;
          description
          "If a connected MQTT client gets disabled
          ({{param|Status}} is either
          {{enum|Connecting|Status}} or
          {{enum|Connected|Status}}) then the MQTT client has
          to send a MQTT DISCONNECT message to disconnect from
          the MQTT broker ({{bibref|MQTT31|3.14}} or
          {{bibref|MQTT311|3.14}}), before setting the
          {{param|Status}} to {{enum|Disabled|Status}}.";
          type boolean;
        }
        leaf Status {
          config false;
          description
          "The {{enum|Error}} value MAY be used by the CPE to
          indicate a locally defined error condition.";
          type enumeration {
            enum "Disabled";
            enum "Connecting";
            enum "Connected";
            enum "Error_Misconfigured";
            enum "Error_BrokerUnreachable";
            enum "Error";
          }
        }
        leaf ClientID {
          config true;
          description
          "A change of this parameter is only communicated to
          the MQTT broker with the next MQTT CONNECT message.
          If the change needs to be applied immediately, the
          parameter {{param|ForceReconnect}} has to be set as
          well.";
          type string {
            length "1..23";
          }
        }
        leaf Username {
          config true;
          description
          "If this parameter is {{empty}} no authentication
          parameters are sent in the MQTT CONNECT message.";
          type string {
            length "0..256";
          }
        }
        leaf Password {
          config true;
          description
          "This password is only sent in the MQTT CONNECT
          message if {{param|Username}} is not {{empty}}.";
          type string {
            length "0..256";
          }
        }
        leaf TransportProtocol {
          config true;
          description
          "Indicates the transport protocol to be used for the
          MQTT broker connection.";
          type string;
          default "TCP/IP";
          must ". = ../../Capabilities/TransportProtocolSupported";
        }
        leaf ProtocolVersion {
          config true;
          description
          "Specifies the MQTT protocol version used in the
          communication with the MQTT broker.";
          type string;
          must ". = ../../Capabilities/ProtocolVersionsSupported";
        }
        leaf CleanSession {
          config true;
          description
          "A change of this parameter is only effective after
          the next MQTT CONNECT message to the MQTT broker.  If
          the change needs to be applied immediately, the
          parameter {{param|ForceReconnect}} has to be set as
          well.";
          type boolean;
          default "true";
        }
        leaf MessageRetryTime {
          config true;
          description
          "Message retry time in {{units}} defines the wait time
          before a MQTT message that expects a response (QoS
          value of message is > 0, or PUBLISH, PUBREL,
          SUBSCRIBE, UNSUBSCRIBE message) is resent, because
          the response is not received (see
          {{bibref|MQTT31|4.2}} and {{bibref|MQTT311|4.4}}).";
          type uint32 {
            range "1..max";
          }
          default "5";
        }
        leaf ConnectRetryTime {
          config true;
          description
          "A failure can either be on the connection level (the
          TCP/IP or TLS can not be established) or on the
          Protocol level, the MQTT client does not receive a
          MQTT CONNACK message on a MQTT CONNECT message sent.";
          type uint32 {
            range "1..max";
          }
          default "30";
        }
        leaf KeepAliveTime {
          config true;
          description
          "A change of this parameter is only effective after
          the next MQTT CONNECT message to the MQTT broker.  If
          the change needs to be applied immediately, the
          parameter {{param|ForceReconnect}} has to be set as
          well.";
          type uint32 {
            range "min..65535";
          }
          default "60";
        }
        leaf ForceReconnect {
          config true;
          description
          "This action parameter may be used to immediately
          apply changes in the MQTT connection settings.";
          type boolean;
        }
        leaf BrokerAddress {
          config true;
          description
          "Host name or IP address of the MQTT Broker.";
          type string {
            length "0..256";
          }
        }
        leaf BrokerPort {
          config true;
          description
          "Port number of the MQTT broker.";
          type uint32 {
            range "1..65535";
          }
          default "1883";
        }
        leaf WillEnable {
          config true;
          description
          "If the connection gets enabled and this parameter is
          set to {{true}} and either the parameter
          {{param|WillTopic}} or {{param|WillValue}} are
          {{empty}}, the CPE MUST set the {{param|Status}} to
          {{enum|Error_Misconfigured|Status}} (see
          {{bibref|MQTT311|3.1.2.5}}).";
          type boolean;
        }
        leaf WillTopic {
          config true;
          description
          "If the will handling is enabled (Paramter
          {{param|WillEnable}} is set to {{true}}) and the
          change needs to be applied immediately, the parameter
          {{param|ForceReconnect}} has to be set as well.";
          type string;
        }
        leaf WillValue {
          config true;
          description
          "If the will handling is enabled (Paramter
          {{param|WillEnable}} is set to {{true}}) and the
          change needs to be applied immediately, the parameter
          {{param|ForceReconnect}} has to be set as well.";
          type string;
        }
        leaf WillQoS {
          config true;
          description
          "If the will handling is enabled (Paramter
          {{param|WillEnable}} is set to {{true}}) and the
          change needs to be applied immediately, the parameter
          {{param|ForceReconnect}} has to be set as well.";
          type uint32 {
            range "0..2";
          }
        }
        leaf WillRetain {
          config true;
          description
          "If the will handling is enabled (Paramter
          {{param|WillEnable}} is set to {{true}}) and the
          change needs to be applied immediately, the parameter
          {{param|ForceReconnect}} has to be set as well.";
          type boolean;
        }
        leaf SubscriptionNumberOfEntries {
          config false;
          description
          "{{numentries}}";
          type uint32;
        }
        list Subscription {
          key "Topic";
          unique "Alias";
          config true;
          description
          "The MQTT client MUST subscribe with the MQTT broker
          for all subscription instances, whose parameter
          {{param|Enable}} is set to {{true}}, when it
          establishes a new connection to the MQTT broker.
          Disabled subscription instances with {{param|Enable}}
          set to {{false}} will be ignored during connection
          establishment.";
          leaf Alias {
            config true;
            description
            "{{datatype|expand}}";
            type Alias;
          }
          leaf Enable {
            config true;
            description
            "The actual status of the subscription is indicated
            with {{param|Status}}.";
            type boolean;
          }
          leaf Status {
            config false;
            description
            "If the {{param|Enable}} is set to {{false}} the
            status MUST be either {{enum|Unsubscribed}} or if
            the unsubscription failed {{enum|Error}}.";
            type enumeration {
              enum "Unsubscribed";
              enum "Subscribed";
              enum "Subscribing";
              enum "Unsubscribing";
              enum "Error";
            }
          }
          leaf Topic {
            config true;
            description
            "Name of the subscribed topic.  Topic names may
            contain wildcards according to the rules specified
            in {{bibref|MQTT31|Appendix A}} and
            {{bibref|MQTT311|4.7}}.";
            type string {
              length "0..65535";
            }
          }
          leaf QoS {
            config true;
            description
            "The MQTT QoS level assigned with the subscription
            (see {{bibref|MQTT31|4.1}} and
            {{bibref|MQTT311|4.3}}).";
            type uint32 {
              range "0..2";
            }
          }
        }
        container Stats {
          description
          "The CPE MUST reset the Stats parameters after the
          MQTT client gets (re-)enabled or if the MQTT client
          connects with a new MQTT broker (e.g.
          {{param|#.BrokerAddress}} has changed). The CPE MAY
          retain the values across a reboot if it reconnects
          with the same MQTT broker.";
          leaf BrokerConnectionEstablished {
            config false;
            description
            "Time when the MQTT broker connection was
            established.";
            type yang:date-and-time;
          }
          leaf LastPublishMessageSent {
            config false;
            description
            "Time when the last publish message was sent to the
            MQTT broker.";
            type yang:date-and-time;
          }
          leaf LastPublishMessageReceived {
            config false;
            description
            "Time when the last publish message was received
            from the MQTT broker.";
            type yang:date-and-time;
          }
          leaf PublishSent {
            config false;
            description
            "Number of publish messages sent to the MQTT broker.";
            type yang:counter32;
          }
          leaf PublishReceived {
            config false;
            description
            "Number of publish messages received from to the
            MQTT broker.";
            type yang:counter32;
          }
          leaf SubscribeSent {
            config false;
            description
            "Number of subscribe messages sent to the MQTT
            broker.";
            type yang:counter32;
          }
          leaf UnSubscribeSent {
            config false;
            description
            "Number of unsubscribe messages sent to the MQTT
            broker.";
            type yang:counter32;
          }
          leaf MQTTMessagesSent {
            config false;
            description
            "Total number of MQTT messages sent to the MQTT
            broker.";
            type yang:counter32;
          }
          leaf MQTTMessagesReceived {
            config false;
            description
            "Total number of MQTT messages received from the
            MQTT broker.";
            type yang:counter32;
          }
          leaf ConnectionErrors {
            config false;
            description
            "Number of connection errors.";
            type yang:counter32;
          }
          leaf PublishErrors {
            config false;
            description
            "Number of errors which prevented sending publish
            messages.";
            type yang:counter32;
          }
        }
      }
      list Broker {
        key "Name";
        unique "Alias";
        config true;
        description
        "MQTT broker table.  Contains a list of configured MQTT
        brokers.";
        leaf Alias {
          config true;
          description
          "{{datatype|expand}}";
          type Alias;
        }
        leaf Name {
          config true;
          description
          "The textual name of the MQTT broker.";
          type string {
            length "0..64";
          }
        }
        leaf Enable {
          config true;
          description
          "Allows to enable or disable the MQTT broker.";
          type boolean;
        }
        leaf Status {
          config false;
          description
          "The \"{{enum|Error}}\" value MAY be used by the CPE
          to indicate a locally defined error condition.";
          type enumeration {
            enum "Disabled";
            enum "Enabled";
            enum "Error_Misconfigured";
            enum "Error";
          }
        }
        leaf Port {
          config true;
          description
          "Port used by the MQTT Broker.";
          type uint32 {
            range "1..65535";
          }
          default "1883";
        }
        leaf Interface {
          config true;
          description
          "If {{empty}} is specified, the CPE MUST bind the MQTT
          broker to all available interfaces.";
          type string {
            length "0..256";
          }
        }
        leaf Username {
          config true;
          description
          "If this parameter is {{empty}} no authentication is
          used.";
          type string {
            length "0..256";
          }
        }
        leaf Password {
          config true;
          description
          "This password is only used if {{param|Username}} is
          not {{empty}}.";
          type string {
            length "0..256";
          }
        }
        leaf BridgeNumberOfEntries {
          config false;
          description
          "{{numentries}}";
          type uint32;
        }
        list Bridge {
          key "Name";
          unique "Alias";
          config true;
          description
          "Configures MQTT bridges, which are used to
          communicate with other MQTT brokers.";
          leaf Alias {
            config true;
            description
            "{{datatype|expand}}";
            type Alias;
          }
          leaf Name {
            config true;
            description
            "The textual name of the MQTT bridge used for
            identification.";
            type string {
              length "0..64";
            }
          }
          leaf Enable {
            config true;
            description
            "Allows to enable or disable the MQTT Bridge.";
            type boolean;
          }
          leaf Status {
            config false;
            description
            "The {{enum|Error}} value MAY be used to indicate a
            locally defined error condition.";
            type enumeration {
              enum "Disabled";
              enum "Connecting";
              enum "Connected";
              enum "Enabled";
              enum "Error_Misconfigured";
              enum "Error_BrokerUnreachable";
              enum "Error";
            }
          }
          leaf ClientID {
            config true;
            description
            "A change of this parameter is only communicated to
            the remote MQTT broker with the next MQTT CONNECT
            message.  If the change needs to be applied
            immediately, the parameter {{param|ForceReconnect}}
            has to be set as well.";
            type string {
              length "1..23";
            }
          }
          leaf Username {
            config true;
            description
            "If this parameter is {{empty}} no authentication
            parameters are sent in the MQTT CONNECT message.";
            type string {
              length "0..256";
            }
          }
          leaf Password {
            config true;
            description
            "The password is only sent if {{param|Username}} is
            not {{empty}}.";
            type string {
              length "0..256";
            }
          }
          leaf TransportProtocol {
            config true;
            description
            "Indicates the transport protocol to be used for the
            MQTT bridge connection.";
            type string;
            default "TCP/IP";
            must ". = ../../../Capabilities/TransportProtocolSupported";
          }
          leaf ProtocolVersion {
            config true;
            description
            "Specifies the MQTT protocol version used in the
            MQTT bridge connection.";
            type string;
            must ". = ../../../Capabilities/ProtocolVersionsSupported";
          }
          leaf CleanSession {
            config true;
            description
            "A change of this parameter is only effective after
            the next MQTT CONNECT message to the remote MQTT
            broker.  If the change needs to be applied
            immediately, the parameter {{param|ForceReconnect}}
            has to be set as well.";
            type boolean;
            default "true";
          }
          leaf MessageRetryTime {
            config true;
            description
            "Message retry time in {{units}} defines the wait
            time before a MQTT message that expects a response
            (QoS value of message is > 0, or PUBLISH, PUBREL,
            SUBSCRIBE, UNSUBSCRIBE message) is resent, because
            the response is not received (see
            {{bibref|MQTT31|4.2}} and {{bibref|MQTT311|4.4}}).";
            type uint32 {
              range "1..max";
            }
            default "5";
          }
          leaf ConnectRetryTime {
            config true;
            description
            "A failure can either be on the connection level
            (e.g.  the TCP/IP or TLS conection can not be
            established) or on the Protocol level, the MQTT
            client does not receive a MQTT CONNACK message on a
            MQTT CONNECT message sent.";
            type uint32 {
              range "1..max";
            }
            default "30";
          }
          leaf KeepAliveTime {
            config true;
            description
            "A change of this parameter is only effective after
            the next MQTT CONNECT message to the remote MQTT
            broker.  If the change needs to be applied
            immediately, the parameter {{param|ForceReconnect}}
            has to be set as well.";
            type uint32 {
              range "min..65535";
            }
            default "60";
          }
          leaf ForceReconnect {
            config true;
            description
            "This action parameter may be used to immediately
            apply changes in the MQTT connection settings.";
            type boolean;
          }
          leaf ServerSelectionAlgorithm {
            config true;
            description
            "The algorithm used to select a server entry from
            the {{object|Server}} table";
            type enumeration {
              enum "Priority" {
                description
                "Select the server from the {{object|Server.}}
                table according to the sequence defined with
                the {{param|Server.{i}.Priority}} and
                {{param|Server.{i}.Weight}} values.";
              }
              enum "RoundRobin" {
                description
                "Select the servers round robin.";
              }
              enum "Random" {
                description
                "Select the servers randomly.";
              }
            }
          }
          leaf ServerConnection {
            config false;
            description
            "{{reference|the {{object|Server.}} instance that is
            used for this {{object}}, while the
            {{param|Status}} is {{enum|Connecting|Status}} or
            {{enum|Connected|Status}}. If the MQTT bridge is
            not connected the value MUST be an empty string}}";
            type string;
          }
          leaf ServerNumberOfEntries {
            config false;
            description
            "{{numentries}}";
            type uint32;
          }
          leaf SubscriptionNumberOfEntries {
            config false;
            description
            "{{numentries}}";
            type uint32;
          }
          list Server {
            key "Address Port";
            unique "Alias";
            config true;
            description
            "Any attempt to delete an instance, which is
            currently in use
            ({{param|##.Bridge.{i}.ServerConnection}} refers to
            the instance to be deleted), has to be rejected.";
            leaf Enable {
              config true;
              description
              "Enables or disables this {{object}}.";
              type boolean;
              default "false";
            }
            leaf Alias {
              config true;
              description
              "{{datatype|expand}}";
              type Alias;
            }
            leaf Priority {
              config true;
              description
              "This value is only used if
              {{param|##.Bridge.{i}.ServerSelectionAlgorithm}}
              is set to
              {{enum|Priority|##.Bridge.{i}.ServerSelectionAlgorithm}}.";
              type uint32 {
                range "0..65535";
              }
            }
            leaf Weight {
              config true;
              description
              "This value is only used if
              {{param|##.Bridge.{i}.ServerSelectionAlgorithm}}
              is set to
              {{enum|Priority|##.Bridge.{i}.ServerSelectionAlgorithm}}.";
              type int64 {
                range "-1..65535";
              }
            }
            leaf Address {
              config true;
              description
              "If the value of this parameter is a FQDN that
              resolves to multiple addresses then each address
              SHOULD be attempted (in an
              implementation-specific order) until a connection
              can be made or all addresses are exhausted, in
              which case the next {{object}} instance (based on
              rules defined over the selected
              {{param|##.Bridge.{i}.ServerSelectionAlgorithm}})
              SHOULD be used.";
              type string {
                length "0..256";
              }
            }
            leaf Port {
              config true;
              description
              "Port number of the MQTT broker server this
              {{object|##.Bridge}} connects to.";
              type uint32 {
                range "1..65535";
              }
            }
          }
          list Subscription {
            key "Topic Direction";
            unique "Alias";
            config true;
            description
            "List of MQTT subscriptions handled over the bridge.";
            leaf Alias {
              config true;
              description
              "{{datatype|expand}}";
              type Alias;
            }
            leaf Enable {
              config true;
              description
              "The actual status of the subscription is
              indicated with {{param|Status}}.";
              type boolean;
            }
            leaf Status {
              config false;
              description
              "The {{enum|Error}} value indicates that an error
              occured (e.g.  an subscription could not be made
              with the remote MQTT broker) and the subscription
              is not in use.";
              type enumeration {
                enum "Enabled";
                enum "Disabled";
                enum "Error";
              }
            }
            leaf Topic {
              config true;
              description
              "Name of the subscribed topic.  Topic names may
              contain wildcards according to the rules
              specified in {{bibref|MQTT31|Appendix A}} and
              {{bibref|MQTT311|4.7}}.";
              type string {
                length "0..65535";
              }
            }
            leaf Direction {
              config true;
              description
              "The direction of the subscription.  {{enum}}.";
              type enumeration {
                enum "out" {
                  description
                  "Indicates that all matching topics will be
                  sent over the bridge to the next MQTT broker.";
                }
                enum "in" {
                  description
                  "Indicates that all matching topics will be
                  received over the bridge from the next MQTT
                  broker.";
                }
                enum "both" {
                  description
                  "Indicates that all matching topics will be
                  sent and received over the bridge.";
                }
              }
            }
            leaf QoS {
              config true;
              description
              "The MQTT QoS level assigned with the subscription
              (see {{bibref|MQTT31|4.1}} and
              {{bibref|MQTT311|4.3}}).";
              type uint32 {
                range "0..2";
              }
            }
            leaf LocalPrefix {
              config true;
              description
              ":: MQTT broker receives message with topic
              \"/local/bus/tr181\" from a MQTT client => MQTT
              broker sends topic \"/bus/tr181\" to remote MQTT
              broker";
              type string;
            }
            leaf RemotePrefix {
              config true;
              description
              ":: MQTT broker receives message with topic
              \"/local/bus/tr181\" from a MQTT client => MQTT
              broker sends topic \"/remote/bus/tr181\" to
              remote MQTT broker";
              type string;
            }
          }
        }
        container Stats {
          description
          "The MQTT broker statistics values.  These will reset
          with each MQTT broker start, either after reboot or
          if the MQTT broker gets (re-)enabled.";
          leaf TotalNumberOfClients {
            config false;
            description
            "Total number of MQTT clients registered with the
            MQTT broker.";
            type uint32;
          }
          leaf NumberOfActiveClients {
            config false;
            description
            "Number of MQTT clients, which have a connection
            with the MQTT broker established.";
            type uint32;
          }
          leaf NumberOfInactiveClients {
            config false;
            description
            "Number of MQTT clients, which have no connection
            with the MQTT broker established.";
            type uint32;
          }
          leaf Subscriptions {
            config false;
            description
            "Number of subscriptions held by the MQTT broker.";
            type uint32;
          }
          leaf PublishSent {
            config false;
            description
            "Number of publish messages sent by the MQTT broker.";
            type yang:counter32;
          }
          leaf PublishReceived {
            config false;
            description
            "Number of publish messages received by the MQTT
            broker.";
            type yang:counter32;
          }
          leaf MQTTMessagesSent {
            config false;
            description
            "Total number of MQTT messages sent by the MQTT
            broker.";
            type yang:counter32;
          }
          leaf MQTTMessagesReceived {
            config false;
            description
            "Total number of MQTT messages received by the MQTT
            broker.";
            type yang:counter32;
          }
          leaf ConnectionErrors {
            config false;
            description
            "Number of connection errors.";
            type yang:counter32;
          }
          leaf PublishErrors {
            config false;
            description
            "Number of errors which prevented sending publish
            messages";
            type yang:counter32;
          }
        }
      }
    }
    container DynamicDNS {
      description
      "Properties for Dynamic DNS.";
      leaf ClientNumberOfEntries {
        config false;
        description
        "{{numentries}}";
        type uint32;
      }
      leaf ServerNumberOfEntries {
        config false;
        description
        "{{numentries}}";
        type uint32;
      }
      leaf-list SupportedServices {
        config false;
        description
        "List of Dynamic DNS service names that are supported by
        the CPE.";
        type string;
      }
      list Client {
        key "Server Username";
        unique "Alias";
        config true;
        description
        "For enabled table entries, if {{param|Server}} is not a
        valid reference then the table entry is inoperable and
        the CPE MUST set the {{param|Status}} to
        {{enum|Error_Misconfigured|Status}}.";
        leaf Enable {
          config true;
          description
          "Enables or disables this Dynamic DNS Client.";
          type boolean;
        }
        leaf Status {
          config false;
          description
          "Status of this Dynamic DNS Client.";
          type enumeration {
            enum "Connecting" {
              description
              "The Dynamic DNS Client is trying to connect to
              the Server.";
            }
            enum "Authenticating" {
              description
              "The Dynamic DNS Client is in the authentication
              phase.";
            }
            enum "Updated" {
              description
              "The Dynamic DNS Client has performed an update
              request since the last IP address change.";
            }
            enum "Error_Misconfigured" {
              description
              "Error due to configuration.";
            }
            enum "Error" {
              description
              "An error has occurred during the communication
              with the Server.  The {{param|LastError}}
              parameter is updated with the detail of this
              error.";
            }
            enum "Disabled" {
              description
              "The Client is disabled.";
            }
          }
        }
        leaf Alias {
          config true;
          description
          "{{datatype|expand}}";
          type Alias;
        }
        leaf LastError {
          config false;
          description
          "The parameter MAY instead indicate a vendor-specific
          cause, which MUST use the format defined in
          {{bibref|TR-106}}.";
          type enumeration {
            enum "NO_ERROR";
            enum "MISCONFIGURATION_ERROR";
            enum "DNS_ERROR";
            enum "CONNECTION_ERROR";
            enum "AUTHENTICATION_ERROR";
            enum "TIMEOUT_ERROR";
            enum "PROTOCOL_ERROR";
          }
        }
        leaf Server {
          config true;
          description
          "{{reference}}";
          type string {
            length "0..256";
          }
        }
        leaf Interface {
          config true;
          description
          "If an empty string is specified, the CPE MUST use its
          routing policy (Forwarding table entries), to
          determine the appropriate interface.";
          type string {
            length "0..256";
          }
        }
        leaf Username {
          config true;
          description
          "Username used by this Dynamic DNS Client to
          authenticate with the Server.";
          type string {
            length "0..256";
          }
        }
        leaf Password {
          config true;
          description
          "Password used by this Dynamic DNS Client to
          authenticate with the Server.";
          type string {
            length "0..256";
          }
        }
        leaf HostnameNumberOfEntries {
          config false;
          description
          "{{numentries}}";
          type uint32;
        }
        list Hostname {
          key "Name";
          config true;
          description
          "Each table entry represents a fully qualified domain
          name updated by this Dynamic DNS Client.";
          leaf Enable {
            config true;
            description
            "Enables or disables this Hostname.";
            type boolean;
          }
          leaf Status {
            config false;
            description
            "Status of this Hostname.";
            type enumeration {
              enum "Registered" {
                description
                "The Hostname has been updated with the current
                IP address.";
              }
              enum "UpdateNeeded" {
                description
                "The IP address has changed since last update.";
              }
              enum "Updating" {
                description
                "The Client is trying to update this Hostname.";
              }
              enum "Error" {
                description
                "The Hostname doesn't exist for this Dynamic DNS
                account.";
              }
              enum "Disabled" {
                description
                "The Hostname is disabled.";
              }
            }
          }
          leaf Name {
            config true;
            description
            "If the name is set to another value, the Client
            MUST immediately send an update request to the
            Server.";
            type string {
              length "0..256";
            }
          }
          leaf LastUpdate {
            config false;
            description
            "The date time of the last successful update of this
            name to the Dynamic DNS Server.";
            type yang:date-and-time;
          }
        }
      }
      list Server {
        key "Name";
        unique "Alias";
        config true;
        description
        "Table of Dynamic DNS servers available for this CPE.";
        leaf Enable {
          config true;
          description
          "Enables or disables Dynamic DNS Server.";
          type string {
            length "0..64";
          }
        }
        leaf Name {
          config true;
          description
          "The textual name of the Dynamic DNS Server.";
          type string {
            length "0..64";
          }
        }
        leaf Alias {
          config true;
          description
          "{{datatype|expand}}";
          type Alias;
        }
        leaf ServiceName {
          config true;
          description
          "{{reference}}";
          type string {
            length "0..256";
          }
          must ". = /Device/DynamicDNS/SupportedServices";
        }
        leaf ServerAddress {
          config true;
          description
          "Host name or IP address of the Dynamic DNS server.";
          type string {
            length "0..256";
          }
        }
        leaf ServerPort {
          config true;
          description
          "Port number of the Dynamic DNS server.";
          type uint32 {
            range "0..65535";
          }
        }
        leaf-list SupportedProtocols {
          config false;
          description
          "Indicates the protocols that are supported by the CPE
          for sending requests to the Dynamic DNS server.
          {{list}} This list depends on the Dynamic DNS service
          defined by the {{param|ServiceName}} parameter.";
          type enumeration {
            enum "HTTP" {
              description
              "As defined in {{bibref|RFC2616}}";
            }
            enum "HTTPS" {
              description
              "As defined in {{bibref|RFC2818}}";
            }
          }
        }
        leaf Protocol {
          config true;
          description
          "Indicates the protocol used to send requests to the
          Dynamic DNS server.";
          type string;
          must ". = ../SupportedProtocols";
        }
        leaf CheckInterval {
          config true;
          description
          "A value of zero indicates that the CPE knows when IP
          changes and doesn’t need to check it periodically.";
          type uint32;
        }
        leaf RetryInterval {
          config true;
          description
          "Initial retry interval (in {{units}}) after a failed
          request.  This parameter can be used as a fixed value
          or as part of a retry interval calculation.";
          type uint32;
        }
        leaf MaxRetries {
          config true;
          description
          "A value of 0 means that there are no retries after a
          failed request.";
          type uint32;
        }
      }
    }
    container LEDs {
      description
      "This object describes the LEDs on the device.";
      leaf LEDNumberOfEntries {
        config false;
        description
        "{{numentries}}";
        type uint32;
      }
      list LED {
        key "Name";
        unique "Alias";
        config true;
        description
        "When the value of the {{param|RelativeXPosition}} and
        {{param|RelativeYPosition}} parameters are 0, this
        indicates that the position of the LED is unknown.";
        leaf Alias {
          config true;
          description
          "{{datatype|expand}}";
          type Alias;
        }
        leaf Name {
          config true;
          description
          "The internal name used to identify this LED.";
          type string;
        }
        leaf Status {
          config false;
          description
          "The status of the LED.";
          type enumeration {
            enum "Disabled" {
              description
              "The LED is currently not in use.";
            }
            enum "InUse" {
              description
              "The LED is currently being used by the CPE.";
            }
            enum "Controlled" {
              description
              "Indicates that the LED is controlled from an
              electronic circuit which cannot be monitored.";
            }
            enum "Error" {
              description
              "The LED status cannot be determined by the CPE.";
            }
          }
        }
        leaf Reason {
          config false;
          description
          "The textual purpose that represents the visual
          display of the LED (e.g., Broadband Down).";
          type string;
        }
        leaf CyclePeriodRepetitions {
          config false;
          description
          "The number of cycle periods left for this LED. As
          each cycle period is completed this parameter is
          reduced by 1. A value of -1 indicates an infinite
          number of cycle period repetitions.";
          type int32 {
            range "-1..max";
          }
        }
        leaf Location {
          config false;
          description
          "The location of the LED as the user looks at the
          front of the device in its typical orientation (e.g.,
          on-end, flat).";
          type enumeration {
            enum "Front";
            enum "Back";
            enum "Left";
            enum "Right";
            enum "Top";
            enum "Bottom";
          }
        }
        leaf RelativeXPosition {
          config false;
          description
          "The relative x position of the LED from left to right
          (x) and top to bottom (y) as the user looks at the
          device from the orientation identified in the
          {{param|Location}} parameter in its typical
          orientation (e.g., on-end, flat).";
          type uint32;
        }
        leaf RelativeYPosition {
          config false;
          description
          "The relative y position of the LED from left to right
          (x) and top to bottom (y) as the user looks at the
          device from the orientation identified in the
          {{param|Location}} parameter in its typical
          orientation (e.g., on-end, flat).";
          type uint32;
        }
        leaf CycleElementNumberOfEntries {
          config false;
          description
          "{{numentries}}";
          type uint32;
        }
        list CycleElement {
          key "Order";
          unique "Alias";
          config true;
          description
          "The length of the complete LED cycle is the sum of
          the Duration parameters for all of the entries in
          this table.";
          leaf Alias {
            config true;
            description
            "{{datatype|expand}}";
            type Alias;
          }
          leaf Enable {
            config true;
            description
            "Enables or disables this {{object}} instance.";
            type boolean;
          }
          leaf Order {
            config true;
            description
            "The relative order of this {{object}} in the LED's
            cycle period.";
            type uint32 {
              range "1..max";
            }
          }
          leaf Color {
            config true;
            description
            "Note: If the parameter is set to an unsupported
            color the CPE MUST NOT infer a different color.";
            type yang:hex-string {
              length "3";
            }
          }
          leaf Duration {
            config true;
            description
            "The duration, in {{units}}, for this element of the
            cycle period.";
            type uint32;
          }
          leaf FadeInterval {
            config true;
            description
            "The transition to the target illumination
            characteristics is uniformly interpolated
            \"perceptually\" over the value of this {{param}}
            parameter.";
            type uint32;
          }
        }
        container CurrentCycleElement {
          description
          "This object describes the status of the current cycle
          element for this LED.";
          leaf CycleElementReference {
            config false;
            description
            "{{reference}} If the LED instances does not have a
            current cycle element active, this parameter MUST
            be set to {{empty}}.";
            type string;
          }
          leaf Color {
            config false;
            description
            "The color, formatted as RGB hexadecimal notation
            (e.g., FF0088), that is currently being displayed
            by the LED.";
            type yang:hex-string {
              length "3";
            }
          }
          leaf Duration {
            config false;
            description
            "The remaining duration, in {{units}}, for this
            element of the cycle period.";
            type uint32;
          }
        }
      }
    }
    container BASAPM {
      description
      "This object represents the objects necessary to manage
      and control the functionality for tests that utilize the
      Broadband Access Service Attributes and Performance
      Metrics measurement test framework as defined in by
      {{bibref|TR-304}}.";
      leaf MeasurementEndpointNumberOfEntries {
        config false;
        description
        "{{numentries}}";
        type uint32;
      }
      list MeasurementEndpoint {
        key "MeasurementAgent";
        unique "Alias";
        config true;
        description
        "This object represents the measurement endpoint that
        provides additional contextual information regarding
        the measurement agent.";
        leaf Alias {
          config true;
          description
          "{{datatype|expand}}";
          type Alias;
        }
        leaf Enable {
          config true;
          description
          "This parameter is based on ''ifAdminStatus'' from
          {{bibref|RFC2863}}.";
          type boolean;
        }
        leaf MeasurementAgent {
          config true;
          description
          "{{reference|a {{object|##.LMAP.MeasurementAgent}}
          object that is associated with this measurement
          endpoint.}}";
          type string;
        }
        leaf DeviceOwnership {
          config true;
          description
          "{{enum}}";
          type enumeration {
            enum "ISP" {
              description
              "ISP Owned Device";
            }
            enum "Customer" {
              description
              "Customer Owned Device";
            }
          }
        }
        leaf OperationalDomain {
          config true;
          description
          "This parameter describes the operational domain for
          this measurement endpoint";
          type string {
            length "0..256";
          }
        }
        leaf InternetDomain {
          config true;
          description
          "The top level Internet domain used to identify this
          measurement endpoint.";
          type string {
            length "0..64";
          }
        }
        leaf UseMeasurementEndpointInReports {
          config true;
          description
          "If the value of this parameter is {{false}} then the
          Measurement Endpoint MUST not be included in
          measurement reports.";
          type boolean;
        }
        container ISPDevice {
          description
          "This object represents the information necessary to
          utilize an ISP owned device within the measurement
          endpoint.";
          leaf ReferencePoint {
            config true;
            description
            "{{enum}}";
            type enumeration {
              enum "STP" {
                description
                "Internet Source Test Point";
              }
              enum "IDTP" {
                description
                "Internet Drain Test Point";
              }
              enum "RNTP" {
                description
                "Regional Network Test Point";
              }
              enum "IRTP" {
                description
                "Internal Regional Test Point";
              }
              enum "MTP" {
                description
                "Metro Test Point";
              }
              enum "IATP" {
                description
                "Internal Access Test Point";
              }
              enum "UNITP" {
                description
                "User Network Interface Test Point";
              }
              enum "CEDTP" {
                description
                "Customer End Device Test Point";
              }
            }
          }
          leaf GeographicalLocation {
            config true;
            description
            "{{reference|a {{object|###.DeviceInfo.Location}}
            object that describes the geographic location of
            the measurement endpoint}}";
            type string;
          }
        }
        container CustomerDevice {
          description
          "This object represents the information necessary to
          utilize customer owned device within the measurement
          endpoint.";
          leaf EquipmentIdentifier {
            config true;
            description
            "This parameter describes the customer equipment
            identifier of the measurement endpoint.";
            type string {
              length "0..64";
            }
          }
          leaf CustomerIdentifier {
            config true;
            description
            "The unique customer identifier within the
            operational domain for this measurement endpoint.";
            type string {
              length "0..256";
            }
          }
        }
      }
    }
    container LMAP {
      description
      "This object represents the objects necessary to manage
      and control the functionality for Large-Scale Measurement
      of Broadband Performance{{bibref|RFC7594}} as defined in
      by {{bibref|LMAPIFM}}.";
      leaf MeasurementAgentNumberOfEntries {
        config false;
        description
        "{{numentries}}";
        type uint32;
      }
      leaf ReportNumberOfEntries {
        config false;
        description
        "{{numentries}}";
        type uint32;
      }
      leaf EventNumberOfEntries {
        config false;
        description
        "{{numentries}}";
        type uint32;
      }
      list MeasurementAgent {
        key "Identifier";
        unique "Alias";
        config true;
        description
        "This object represents the measurement agent that
        performs measurement tasks and reporting functions
        defined in {{bibref|RFC7594}}.";
        leaf Alias {
          config true;
          description
          "{{datatype|expand}}";
          type Alias;
        }
        leaf Enable {
          config true;
          description
          "This parameter is based on ''ifAdminStatus'' from
          {{bibref|RFC2863}}.";
          type boolean;
        }
        leaf Version {
          config false;
          description
          "Version of the measurement agent.";
          type string;
        }
        leaf LastStarted {
          config false;
          description
          "Date and time, based on {{bibref|RFC3339}}, in UTC
          that the measurement agent was successfully started.";
          type yang:date-and-time;
        }
        leaf-list CapabilityTags {
          config false;
          description
          "Capabilities of the measurement agent that cannot be
          expressed elsewhere in the data model.";
          type string;
        }
        leaf Identifier {
          config true;
          description
          "Identifier of the {{object}} instance.";
          type yang:uuid;
        }
        leaf GroupIdentifier {
          config true;
          description
          "Identifier of the measurement group of interest to
          which the measurement agent belongs.";
          type string {
            length "0..256";
          }
        }
        leaf MeasurementPoint {
          config true;
          description
          "Identifier of the measurement point indicating where
          the measurement agent is located on a path as defined
          in [bibref|RFC7398}}.";
          type string {
            length "0..256";
          }
        }
        leaf UseAgentIdentifierInReports {
          config true;
          description
          "If the value of the {{param|Identifier}} parameter is
          not {{empty}} and the value of this parameter is
          {{false}} then the value of the {{param|Identifier}}
          parameter MUST not be included in measurement
          reports.";
          type boolean;
          default "true";
        }
        leaf UseGroupIdentifierInReports {
          config true;
          description
          "If the value of the {{param|GroupIdentifier}}
          parameter is not {{empty}} and the value of this
          parameter is {{false}} then the value of the
          {{param|GroupIdentifier}} parameter MUST not be
          included in measurement reports.";
          type boolean;
          default "false";
        }
        leaf UseMeasurementPointInReports {
          config true;
          description
          "If the value of the {{param|MeasurementPoint}}
          parameter is not {{empty}} and the value of this
          parameter is {{false}} then the value of the
          {{param|MeasurementPoint}} parameter MUST not be
          included in measurement reports.";
          type boolean;
          default "false";
        }
        leaf PublicCredential {
          config true;
          description
          "{{reference|a {{object|##.Security.Certificate}}
          object that is used to identify this measurement
          agent}}";
          type string;
        }
        leaf PrivateCredential {
          config true;
          description
          "{{reference|a {{object|##.Security.Certificate}}
          object that is used to contain the private keys for
          this measurement agent}}";
          type string;
        }
        leaf EventLog {
          config false;
          description
          "{{reference|a {{object|##.DeviceInfo.VendorLogFile}}
          object that is used to record events for this
          measurement agent}}";
          type string;
        }
        leaf TaskCapabilityNumberOfEntries {
          config false;
          description
          "{{numentries}}";
          type uint32;
        }
        leaf ScheduleNumberOfEntries {
          config false;
          description
          "{{numentries}}";
          type uint32;
        }
        leaf TaskNumberOfEntries {
          config false;
          description
          "{{numentries}}";
          type uint32;
        }
        leaf CommunicationChannelNumberOfEntries {
          config false;
          description
          "{{numentries}}";
          type uint32;
        }
        leaf InstructionNumberOfEntries {
          config false;
          description
          "{{numentries}}";
          type uint32;
        }
        list TaskCapability {
          key "Name";
          config false;
          description
          "This object represents a capabilities, in the context
          of a task, that are supported by the measurement
          agent.  Types of capabilities include: Report tasks,
          Configuration Tasks and Instruction Tasks.";
          leaf Name {
            config false;
            description
            "Name of the supported task.";
            type string {
              length "0..256";
            }
          }
          leaf Version {
            config false;
            description
            "Version of the task.";
            type string {
              length "0..256";
            }
          }
          leaf TaskCapabilityRegistryNumberOfEntries {
            config false;
            description
            "{{numentries}}";
            type uint32;
          }
          list Registry {
            key "RegistryEntry";
            config false;
            description
            "This object represents a registry function and an
            associated list of roles supported by this
            measurement agent";
            leaf RegistryEntry {
              config false;
              description
              "A URI ({{bibref|RFC3986}}) that is the value of
              the task registry entry as defined in
              {{bibref|LMAPREG}} or a value for a task that is
              understood by the measurement agent, measurement
              controller and measurement collector.";
              type string;
            }
            leaf-list Roles {
              config false;
              description
              "{{list| representing the roles of the function}}";
              type string {
                length "0..256";
              }
            }
          }
        }
        container Controller {
          description
          "This objects represents the measurement controller
          that is assigned to a measurement agent.";
          leaf ControllerTimeout {
            config true;
            description
            "When the timer reaches the timeout en event is
            raised indicating that connectivity to the
            controller has been lost.";
            type int32 {
              range "0..max";
            }
          }
          leaf-list ControlSchedules {
            config true;
            description
            "This parameter lists the available control
            schedules for invoking control tasks by the
            measurement agent.";
            type string;
          }
          leaf-list ControlTasks {
            config true;
            description
            "This parameter lists the available control tasks
            that can be invoked by the measurement agent.";
            type string;
          }
          leaf-list ControlChannels {
            config true;
            description
            "The measurement agent to measurement controller
            channel is used for conveying results of
            communication sessions with the configuration,
            instruction status and logging information elements
            defined in defined in {{bibref|LMAPIFM}}.";
            type string;
          }
        }
        list Schedule {
          key "Name";
          unique "Alias";
          config true;
          description
          "Note: Actions of an occurrence of this {{object}} are
          gracefully terminated by the defining either the
          {{param|End}} or {{param|Duration}} parameters.  Only
          one of these parameters may be defined at a time.";
          leaf Enable {
            config true;
            description
            "This parameter is based on ''ifAdminStatus'' from
            {{bibref|RFC2863}}.";
            type boolean;
          }
          leaf Alias {
            config true;
            description
            "{{datatype|expand}}";
            type Alias;
          }
          leaf Name {
            config true;
            description
            "Name of the schedule.";
            type string {
              length "0..256";
            }
          }
          leaf State {
            config false;
            description
            "{{enum}}";
            type enumeration {
              enum "Enabled";
              enum "Suppressed";
              enum "Disabled";
              enum "Running";
            }
          }
          leaf Start {
            config true;
            description
            "{{reference|a {{object|##.Event}} object that is
            used define the event to start an occurrence of
            this {{object}}}}";
            type string;
          }
          leaf End {
            config true;
            description
            "{{reference|a {{object|##.Event}} object that is
            used define the event to gracefully terminate all
            actions associated with an occurrence of this
            {{object}}}}.";
            type string;
          }
          leaf Duration {
            config true;
            description
            "When the {{param}} value is not 0, this parameter
            is used define the duration, in {{units}}, where
            after this duration all actions associated with an
            occurrence of this {{object}} are gracefully
            terminated.";
            type uint32;
            default "0";
          }
          leaf-list Tags {
            config true;
            description
            "{{list|each entry represents tags that are to be
            reported together with the measurement results.}}";
            type string;
          }
          leaf-list SuppressionTags {
            config true;
            description
            "{{list|representing the suppression tags to be
            matched}}";
            type string;
          }
          leaf ExecutionMode {
            config true;
            description
            "{{enum}}";
            type enumeration {
              enum "Sequential" {
                description
                "The first Scheduled Action of the
                DestinationOutput is provided the input.";
              }
              enum "Parallel" {
                description
                "The all Scheduled Actions of the
                DestinationOutput are provided the input.";
              }
              enum "Pipelined" {
                description
                "The first Scheduled Action of the
                DestinationOutput is provided the input.";
              }
            }
            default "Pipelined";
          }
          leaf LastInvocation {
            config false;
            description
            "Date and time, based on {{bibref|RFC3339}}, in UTC
            that the {{object}} was invoked by the measurement
            agent.";
            type yang:date-and-time;
          }
          leaf Storage {
            config false;
            description
            "For example the secondary storage can be the
            storage allocated in a file system holding
            temporary data.";
            type uint64;
          }
          leaf ActionNumberOfEntries {
            config false;
            description
            "{{numentries}}";
            type uint32;
          }
          container Stats {
            description
            "This object represents the statistics associated
            with this object.";
            leaf Invocations {
              config false;
              description
              "Number of invocations of this schedule.  This
              counter does not include suppressed invocations
              or invocations that were prevented due to an
              overlap with a previous invocation of this
              schedule.";
              type uint64;
            }
            leaf Suppressions {
              config false;
              description
              "Number of suppressed executions of this schedule.";
              type uint64;
            }
            leaf Overlaps {
              config false;
              description
              "Number of executions prevented due to overlaps
              with a previous invocation of this schedule.";
              type uint64;
            }
            leaf Failures {
              config false;
              description
              "Number of failed executions of this schedule.  A
              failed execution is an execution where at least
              one action failed.";
              type uint64;
            }
          }
          list Action {
            key "Alias";
            config true;
            description
            "This object represents an action that is associated
            with the this {{object|##.Schedule}} object.";
            leaf Enable {
              config true;
              description
              "This parameter is based on ''ifAdminStatus'' from
              {{bibref|RFC2863}}.";
              type boolean;
            }
            leaf Alias {
              config true;
              description
              "{{datatype|expand}}";
              type Alias;
            }
            leaf State {
              config false;
              description
              "The current operational state of the {{object}}.
              {{enum}}";
              type enumeration {
                enum "Enabled";
                enum "Suppressed";
                enum "Disabled";
                enum "Running";
              }
            }
            leaf Order {
              config true;
              description
              "The order of the scheduled action.";
              type uint32;
            }
            leaf Task {
              config true;
              description
              "{{reference|a {{object|##.Task}} object used in
              this scheduled action}}";
              type string;
            }
            leaf-list OutputDestination {
              config true;
              description
              "{{list}} {{reference|a {{object|##.Schedule}}
              object used to receive the output(s) of this
              scheduled action}}";
              type string;
            }
            leaf-list SuppressionTags {
              config true;
              description
              "{{list|representing the suppression tags to be
              matched}}";
              type string;
            }
            leaf-list Tags {
              config true;
              description
              "{{list|each entry represents tags that are to be
              reported together with the measurement results.}}";
              type string;
            }
            leaf Storage {
              config false;
              description
              "For example the secondary storage can be the
              storage allocated in a file system holding
              temporary data.";
              type uint64;
            }
            leaf LastInvocation {
              config false;
              description
              "Date and time, based on {{bibref|RFC3339}}, in
              UTC that the {{object}} was invoked by the
              measurement agent.";
              type yang:date-and-time;
            }
            leaf LastSuccessfulCompletion {
              config false;
              description
              "Date and time, based on {{bibref|RFC3339}}, in
              UTC of a successful completion of the {{object}}.";
              type yang:date-and-time;
            }
            leaf LastSuccessfulStatusCode {
              config false;
              description
              "The status code returned by successful execution
              of the {{object}}. A value of 0 indicates
              successful completion.";
              type int32;
            }
            leaf LastSuccessfulMessage {
              config false;
              description
              "The message associated with the successful
              completion of the {{object}}.";
              type string;
            }
            leaf LastFailedCompletion {
              config false;
              description
              "Date and time, based on {{bibref|RFC3339}}, in
              UTC of a failure to complete the {{object}}.";
              type yang:date-and-time;
            }
            leaf LastFailedStatusCode {
              config false;
              description
              "The status code returned by failed execution of
              the {{object}}. A value of 0 indicates successful
              completion.";
              type int32;
            }
            leaf LastFailedMessage {
              config false;
              description
              "The message associated with the failure to
              complete the task.";
              type string;
            }
            leaf OptionNumberOfEntries {
              config false;
              description
              "{{numentries}}";
              type uint32;
            }
            container Stats {
              description
              "This object represents the statistics associated
              with this object.";
              leaf Invocations {
                config false;
                description
                "Number of invocations of this action.  This
                counter does not include suppressed invocations
                or invocations that were prevented due to an
                overlap with a previous invocation of this
                schedule.";
                type uint64;
              }
              leaf Suppressions {
                config false;
                description
                "Number of suppressed executions of this action.";
                type uint64;
              }
              leaf Overlaps {
                config false;
                description
                "Number of executions prevented due to overlaps
                with a previous invocation of this action.";
                type uint64;
              }
              leaf Failures {
                config false;
                description
                "Number of failed executions of this action.  A
                failed execution is an execution where at least
                one action failed.";
                type uint64;
              }
            }
            list Option {
              key "Name";
              unique "Alias";
              config true;
              description
              "This object represents an option associated with
              the Scheduled Action.  When an option with the
              same Name exists between the Seheduled Action's
              Option and The Task's option, the option of the
              Scheduled Action takes precedence over the option
              associated with the Task.";
              leaf Enable {
                config true;
                description
                "This parameter is based on ''ifAdminStatus''
                from {{bibref|RFC2863}}.";
                type boolean;
              }
              leaf Alias {
                config true;
                description
                "{{datatype|expand}}";
                type Alias;
              }
              leaf Order {
                config true;
                description
                "The order of the Option.";
                type uint32;
              }
              leaf Name {
                config true;
                description
                "When the value of this parameter is equal to
                \"channel\", the option value specifies the
                Communication Channel used for this scheduled
                task.";
                type int32;
              }
              leaf Value {
                config true;
                description
                "The value associated with the Option.";
                type string;
              }
            }
          }
        }
        list Task {
          key "Name";
          unique "Alias";
          config true;
          description
          "Tasks are performed by {{object|##.MeasurementAgent}}
          objects when a {{object|#.Schedule}} object invokes
          the Task.";
          leaf Enable {
            config true;
            description
            "This parameter is based on ''ifAdminStatus'' from
            {{bibref|RFC2863}}.";
            type boolean;
          }
          leaf Alias {
            config true;
            description
            "{{datatype|expand}}";
            type Alias;
          }
          leaf Name {
            config true;
            description
            "Name of the task.";
            type string {
              length "0..256";
            }
          }
          leaf-list Tags {
            config true;
            description
            "{{list|each entry represents tags that are to be
            reported together with the measurement results.}}";
            type string;
          }
          leaf OptionNumberOfEntries {
            config false;
            description
            "{{numentries}}";
            type uint32;
          }
          leaf RegistryNumberOfEntries {
            config false;
            description
            "{{numentries}}";
            type uint32;
          }
          list Registry {
            key "RegistryEntry";
            unique "Alias";
            config true;
            description
            "This object represents a registry function and an
            associated list of roles for this task";
            leaf Enable {
              config true;
              description
              "This parameter is based on ''ifAdminStatus'' from
              {{bibref|RFC2863}}.";
              type boolean;
            }
            leaf Alias {
              config true;
              description
              "{{datatype|expand}}";
              type Alias;
            }
            leaf RegistryEntry {
              config true;
              description
              "A URI ({{bibref|RFC3986}}) that is the value of
              the task registry entry as defined in
              {{bibref|LMAPREG}} or a value for a task that is
              understood by the measurement agent, measurement
              controller and measurement collector.";
              type string;
            }
            leaf-list Roles {
              config true;
              description
              "{{list| representing the roles of the function}}";
              type string {
                length "0..256";
              }
            }
          }
          list Option {
            key "Name";
            unique "Alias";
            config true;
            description
            "This object represents an option associated with
            the task.";
            leaf Enable {
              config true;
              description
              "This parameter is based on ''ifAdminStatus'' from
              {{bibref|RFC2863}}.";
              type boolean;
            }
            leaf Alias {
              config true;
              description
              "{{datatype|expand}}";
              type Alias;
            }
            leaf Order {
              config true;
              description
              "The order of the Option.";
              type uint32;
            }
            leaf Name {
              config true;
              description
              "When the value of this parameter is equal to
              \"channel\", the option value specifies the
              Communication Channel used for this task.";
              type int32;
            }
            leaf Value {
              config true;
              description
              "The value associated with the Option.";
              type string;
            }
          }
        }
        list CommunicationChannel {
          key "Name";
          unique "Alias";
          config true;
          description
          "When this object uses the BulkData capability, a
          {{object|###.BulkData.Profile.{i}}} object instance
          referred to by this object.";
          leaf Enable {
            config true;
            description
            "This parameter is based on ''ifAdminStatus'' from
            {{bibref|RFC2863}}.";
            type boolean;
          }
          leaf Alias {
            config true;
            description
            "{{datatype|expand}}";
            type Alias;
          }
          leaf Name {
            config true;
            description
            "Name of the channel.";
            type string {
              length "0..256";
            }
          }
          leaf UseBulkDataProfile {
            config true;
            description
            "Enables or disables the ability to use a bulk data
            profile for this communication channel";
            type boolean;
          }
          leaf BulkDataProfile {
            config true;
            description
            "{{reference|a {{object|###.BulkData.Profile}}
            object that is used to represent communication
            channel}}";
            type string;
          }
          leaf Target {
            config true;
            description
            "The URL of the LMAP component that is the target of
            this communication channel.";
            type string {
              length "0..256";
            }
          }
          leaf TargetPublicCredential {
            config true;
            description
            "{{reference|a {{object|###.Security.Certificate}}
            object that is used to identify the target of this
            channel}}";
            type string;
          }
          leaf Interface {
            config true;
            description
            "{{reference|an interface object used to restrict
            the data transmitted or received using this channel
            to a specific interface}} If the value of this
            parameter is {{empty}} the data that is transmitted
            or received using this channel is able to use any
            available interface.";
            type string;
          }
        }
        list Instruction {
          key "Alias";
          config true;
          description
          "The {{object}} object defines the instruction to the
          measurement agent by the measurement controller.  At
          most one {{object}} object for the
          {{object|##.MeasurementAgent}} instance is enabled at
          a time.  .";
          leaf Enable {
            config true;
            description
            "This parameter is based on ''ifAdminStatus'' from
            {{bibref|RFC2863}}.";
            type boolean;
          }
          leaf Alias {
            config true;
            description
            "{{datatype|expand}}";
            type Alias;
          }
          leaf LastChange {
            config false;
            description
            "Date and time, based on {{bibref|RFC3339}}, in UTC
            that the {{object}} object or its sub-object's
            configuration was changed by a measurement agent's
            controller.";
            type yang:date-and-time;
          }
          leaf-list InstructionSchedules {
            config true;
            description
            "This parameter lists the available instruction
            schedules for invoking control tasks by the
            measurement agent.";
            type string;
          }
          leaf-list InstructionTasks {
            config true;
            description
            "This parameter lists the available instruction
            tasks that can be invoked by the measurement agent.";
            type string;
          }
          leaf-list ReportChannels {
            config true;
            description
            "This parameter defines the corresponding report
            channels to be used when reporting results of tasks
            to a measurement collector.";
            type string;
          }
          leaf MeasurementSuppressionNumberOfEntries {
            config false;
            description
            "{{numentries}}";
            type uint32;
          }
          list MeasurementSuppression {
            key "Name";
            unique "Alias";
            config true;
            description
            "This object defines the schedules and actions that
            are suppressed based on criteria defined in the
            {{param|SuppressionMatch}} parameter.";
            leaf Enable {
              config true;
              description
              "This parameter is based on ''ifAdminStatus'' from
              {{bibref|RFC2863}}.";
              type boolean;
            }
            leaf Alias {
              config true;
              description
              "{{datatype|expand}}";
              type Alias;
            }
            leaf Name {
              config true;
              description
              "Name of the suppression object.";
              type string {
                length "0..256";
              }
            }
            leaf State {
              config false;
              description
              "The current operational state of the {{object}}.
              {{enum}}";
              type enumeration {
                enum "Enabled";
                enum "Active";
                enum "Disabled";
              }
            }
            leaf StopRunning {
              config true;
              description
              "When {{true}}, the measurement agent is
              instructed to stop running schedules or actions
              that have been matched by this object.";
              type boolean;
              default "false";
            }
            leaf Start {
              config true;
              description
              "{{reference|a {{object|###.Event}} object that is
              used define the event that to start an occurrence
              of this {{object}}}} When {{empty}} the default
              behavior is to perform the suspension event
              immediately.";
              type string;
            }
            leaf End {
              config true;
              description
              "{{reference|a {{object|###.Event}} object that is
              used define the event to gracefully suspend all
              actions associated with an occurrence of this
              {{object}}}} When {{empty}} the default behavior
              is for the suspension period to be indefinite.";
              type string;
            }
            leaf-list SuppressionMatch {
              config true;
              description
              "{{list|representing the match patterns to be used
              for applying suppression to
              {{object|##.Schedule.{i}}} (and their actions)
              and all {{object|##.Schedule.{i}.Action.{i}}}
              object instances that have a matched using their
              SuppressionTags parameters}} The match pattern
              syntax is defined in {{bibref|LMAPIFM}}.";
              type string;
            }
          }
        }
      }
      list Report {
        key "_id";
        leaf "_id" {
          type "uint32";
        }
        config false;
        description
        "When a {{object|##.BulkData.Profile.{i}}} object
        instance is used to communicate a {{object}} instance,
        the CPE adds a
        {{object|##.BulkData.Profile.{i}.Parameter.{i}}} object
        instance referring to this {{object}} object instance.";
        leaf ReportDate {
          config false;
          description
          "The report date and time, based on
          {{bibref|RFC3339}}, that the report was sent to the
          collector.";
          type yang:date-and-time;
        }
        leaf AgentIdentifier {
          config false;
          description
          "Identifier of the measurement agent at the time the
          measurement was run.";
          type yang:uuid;
        }
        leaf GroupIdentifier {
          config false;
          description
          "Identifier of the measurement group of interest to
          which the MA belongs.";
          type string;
        }
        leaf MeasurementPoint {
          config false;
          description
          "Identifier of the measurement point indicating where
          the measurement agent is located on a path as defined
          in {{bibref|RFC7398}}.";
          type string {
            length "0..256";
          }
        }
        leaf ResultNumberOfEntries {
          config false;
          description
          "{{numentries}}";
          type uint32;
        }
        list Result {
          key "ScheduleName ActionName StartTime";
          config false;
          description
          "The {{object}} object provides the meta-data of the
          result report of a single executed action that
          produced the result.";
          leaf TaskName {
            config false;
            description
            "Name of the task that produced the result.";
            type string {
              length "0..256";
            }
          }
          leaf ScheduleName {
            config false;
            description
            "Name of the schedule that produced the result.";
            type string {
              length "0..256";
            }
          }
          leaf ActionName {
            config false;
            description
            "Name of the action that produced the result.";
            type string {
              length "0..256";
            }
          }
          leaf EventTime {
            config false;
            description
            "The date and time, based on {{bibref|RFC3339}},
            that the event that triggered the schedule of the
            action that produced the reported result values in
            UTC.";
            type yang:date-and-time;
          }
          leaf StartTime {
            config false;
            description
            "The date and time, based on {{bibref|RFC3339}},
            that the action started in UTC.";
            type yang:date-and-time;
          }
          leaf EndTime {
            config false;
            description
            "The date and time, based on {{bibref|RFC3339}},
            that the action was completed in UTC.";
            type yang:date-and-time;
          }
          leaf CycleNumber {
            config false;
            description
            "{{pattern}}";
            type string {
              pattern "YYYYMMDD.HHMMSS";
            }
          }
          leaf Status {
            config false;
            description
            "The status code returned by the execution of the
            action.";
            type int32;
          }
          leaf-list Tags {
            config false;
            description
            "{{list|each entry represents tags defined for the
            schedule, task and action objects that produced
            this result}}";
            type string;
          }
          leaf OptionNumberOfEntries {
            config false;
            description
            "{{numentries}}";
            type uint32;
          }
          leaf ResultConflictNumberOfEntries {
            config false;
            description
            "{{numentries}}";
            type uint32;
          }
          leaf ResultReportTableNumberOfEntries {
            config false;
            description
            "{{numentries}}";
            type uint32;
          }
          list Option {
            key "Name";
            config false;
            description
            "This object represents an option associated with
            the task or action object that produced the result.";
            leaf Order {
              config false;
              description
              "The order of the Option.";
              type uint32;
            }
            leaf Name {
              config false;
              description
              "When the value of this parameter is equal to
              \"channel\", the option value specifies the
              Communication Channel used for this task.";
              type int32;
            }
            leaf Value {
              config false;
              description
              "The value associated with the Option.";
              type string;
            }
          }
          list Conflict {
            key "ScheduleName ActionName TaskName";
            config false;
            description
            "This object represents actions that might have
            impacted the results being reported.";
            leaf TaskName {
              config false;
              description
              "Name of the task.";
              type string {
                length "0..256";
              }
            }
            leaf ScheduleName {
              config false;
              description
              "Name of the schedule.";
              type string {
                length "0..256";
              }
            }
            leaf ActionName {
              config false;
              description
              "Name of the action.";
              type string {
                length "0..256";
              }
            }
          }
          list ReportTable {
            key "_id";
            leaf "_id" {
              type "uint32";
            }
            config false;
            description
            "This {{object}} object instances represents a row
            of results.";
            leaf-list ColumnLabels {
              config false;
              description
              "The column labels are ordered with the
              corresponding entries in the {{object|ResultRow}}
              table.";
              type string;
            }
            leaf ResultReportRowNumberOfEntries {
              config false;
              description
              "{{numentries}}";
              type uint32;
            }
            leaf RegistryNumberOfEntries {
              config false;
              description
              "{{numentries}}";
              type uint32;
            }
            list ResultRow {
              key "_id";
              leaf "_id" {
                type "uint32";
              }
              config false;
              description
              "This {{object}} object instances represents a row
              of results for the report.";
              leaf-list Values {
                config false;
                description
                "{{list}} This parameter contains an ordered set
                of values that align to the columns defined in
                the {{param|#.ColumnLabels}} parameter.";
                type string;
              }
            }
            list Registry {
              key "RegistryEntry";
              config false;
              description
              "This object represents a registry function and an
              associated list of roles for this result report.";
              leaf RegistryEntry {
                config false;
                description
                "A URI ({{bibref|RFC3986}}) that is the value of
                the registry entry as defined in
                {{bibref|LMAPREG}} or a value for a task that
                is understood by the measurement agent,
                measurement controller and measurement
                collector.";
                type string;
              }
              leaf-list Roles {
                config false;
                description
                "{{list| representing the roles of the
                function}}";
                type string {
                  length "0..256";
                }
              }
            }
          }
        }
      }
      list Event {
        key "Name";
        unique "Alias";
        config true;
        description
        "This object defines the information associated with an
        event used within the measurement agent.  Event
        instances may be referenced by various objects within
        the LMAP model.";
        leaf Enable {
          config true;
          description
          "This parameter is based on ''ifAdminStatus'' from
          {{bibref|RFC2863}}.";
          type boolean;
        }
        leaf Alias {
          config true;
          description
          "{{datatype|expand}}";
          type Alias;
        }
        leaf Name {
          config true;
          description
          "Name of the Event.";
          type string {
            length "0..256";
          }
        }
        leaf Type {
          config true;
          description
          "{{enum}}";
          type enumeration {
            enum "PeriodicTiming" {
              description
              "Periodic Timing Event.  When selected one or more
              event occurrences are emitted based on the
              parameters defined in the
              {{object|PeriodicTimer}} object.";
            }
            enum "CalendarTiming" {
              description
              "Calendar Timing Event.  When selected one or more
              event occurrences are emitted based on the
              parameters defined in the
              {{object|CalendarTimer}} object.";
            }
            enum "OneOffTiming" {
              description
              "One-off Timing Event.  When selected a single
              event occurrence is emitted based on the
              parameters defined in the {{object|OneOff}}
              object.";
            }
            enum "Immediate" {
              description
              "Immediate Timing Event.  When selected a single
              event occurrence is emitted as soon as possible.";
            }
            enum "Startup" {
              description
              "Startup Timing Event.  When selected a single
              event occurrence is emitted when the
              corresponding measurement agent starts up.";
            }
            enum "ControllerLost" {
              description
              "Controller Lost Event.  When selected a single
              event occurrence is emitted when the connectivity
              to the controller is lost.";
            }
            enum "ControllerConnected" {
              description
              "Controller Connected Event.  When selected a
              single event occurrence is emitted when the
              connectivity to the controller is established.";
            }
          }
          default "Immediate";
        }
        leaf RandomnessSpread {
          config true;
          description
          "The spread, in {{units}}, of the Uniform Discrete
          random distribution algorithm.  A value of 0 means
          that the random algorithm is not applied.";
          type int32;
        }
        leaf CycleInterval {
          config true;
          description
          "The duration of the time interval, in {{units}}, that
          used to calculate cycle numbers.";
          type int32;
        }
        container PeriodicTimer {
          description
          "This object defines a periodic timer instance.  The
          periodic timer instance has attributes for when the
          timer is to begin ({{param|StartTime}}) and end
          ({{param|EndTime}}) as well as the interval to use.";
          leaf StartTime {
            config true;
            description
            "Date and time, based on {{bibref|RFC3339}}, that
            the {{object}} instance is to begin operation.";
            type yang:date-and-time;
          }
          leaf EndTime {
            config true;
            description
            "Date and time, based on {{bibref|RFC3339}}, that
            the {{object}} instance is to end operation.";
            type yang:date-and-time;
          }
          leaf Interval {
            config true;
            description
            "The tolerable duration, in {{units}}, of the
            interval for this {{object}} instance.";
            type uint32;
          }
        }
        container CalendarTimer {
          description
          "If the value of any of the {{param|ScheduleMonths}},
          {{param|ScheduleDaysOfMonth}},
          {{param|ScheduleDaysOfWeek}},
          {{param|ScheduleHoursOfDay}},
          {{param|ScheduleMinutesOfHour}} or
          {{param|ScheduleSecondsOfMinute}} is {{empty}} then
          any actions that use this object will not be invoked.";
          leaf StartTime {
            config true;
            description
            "Date and time that the {{object}} instance is to
            begin this operation.";
            type yang:date-and-time;
          }
          leaf EndTime {
            config true;
            description
            "Date and time that the {{object}} instance is to
            end this operation.";
            type yang:date-and-time;
          }
          leaf ScheduleMonths {
            config true;
            description
            "Each entry in the months of the year list can be a
            numeric value or the name of the month (january
            (1), february (2), march (3), april (4), may (5),
            june (6), july (7), august (8), september (9),
            october (10), november (11), december (12)).";
            type string;
          }
          leaf ScheduleDaysOfMonth {
            config true;
            description
            "This parameter represents either a list of the days
            of the month (1-31) that are applied to the
            schedule or an asterisk (*) that represents all the
            elements of the list.";
            type string;
          }
          leaf ScheduleDaysOfWeek {
            config true;
            description
            "Each entry in the days of the week list can be a
            numeric value or the name of the day (sunday (1),
            monday (2), tuesday (3), wednesday (4), thursday
            (5), friday (6), saturday (7)).";
            type string;
          }
          leaf ScheduleHoursOfDay {
            config true;
            description
            "This parameter represents either a list of the
            hours of the day (0-23) that are applied to the
            schedule or an asterisk (*) that represents all the
            elements of the list.";
            type string;
          }
          leaf ScheduleMinutesOfHour {
            config true;
            description
            "This parameter represents either a list of the
            minutes of the hour (0-59) that are applied to the
            schedule or an asterisk (*) that represents all the
            elements of the list.";
            type string;
          }
          leaf ScheduleSecondsOfMinute {
            config true;
            description
            "This parameter represents either a list of the
            minutes of the hour (0-59) that are applied to the
            schedule or an asterisk (*) that represents all the
            elements of the list.";
            type string;
          }
          leaf EnableScheduleTimezoneOffset {
            config true;
            description
            "When {{false}}, the device's system timezone offset
            is applied to the schedule elements.";
            type boolean;
          }
          leaf ScheduleTimezoneOffset {
            config true;
            description
            "The timezone offset, in {{units}}, to be applied to
            the schedule elements.";
            type int32 {
              range "-23..23";
            }
          }
        }
        container OneOff {
          description
          "This object defines a one off timer instance.";
          leaf StartTime {
            config true;
            description
            "Date and time, based on {{bibref|RFC3339}}, that
            the {{object}} instance is to begin operation.";
            type yang:date-and-time;
          }
        }
      }
    }
  }
}
