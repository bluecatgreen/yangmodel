module openconfig-system-management {

  yang-version "1";

  // namespace
  namespace "http://openconfig.net/yang/system/management";

  prefix "oc-sys-mgmt";

  // import some basic types
  import openconfig-extensions { prefix oc-ext; }
  import openconfig-inet-types { prefix oc-inet; }

  // meta
  organization "OpenConfig working group";

  contact
    "OpenConfig working group
    www.openconfig.net";

  description
    "This module defines configuration and operational state data
    related to management services.";

  oc-ext:openconfig-version "0.1.2";

  revision "2018-11-21" {
    description
      "Add OpenConfig module metadata extensions.";
    reference "0.1.2";
  }

  revision "2018-08-28" {
    description
      "Update description of the ANY enum.";
    reference "0.1.1";
  }

  revision "2018-07-26" {
    description
      "Initial public release";
    reference "0.1.0";
  }

  // OpenConfig specific extensions for module metadata.
  oc-ext:regexp-posix;
  oc-ext:catalog-organization "openconfig";
  oc-ext:origin "openconfig";

  // identity statements

  // typedef statements

  // grouping statements

  grouping system-grpc-server-config {
    description
      "Configuration data for the gRPC server";

    leaf enable {
      type boolean;
      default true;
      description
        "Enables the gRPC server. The gRPC server is enabled by
        default";
    }

    leaf port {
      type oc-inet:port-number;
      description
        "TCP port on which the gRPC server should listen";
    }

    leaf transport-security {
      type boolean;
      description
        "Enables gRPC transport security (e.g., TLS or SSL)";
    }

    leaf certificate-id {
      type string;
      description
        "The certificate ID to be used for authentication";
    }

    leaf-list listen-addresses {
      type union {
        type string;
        type enumeration {
          enum ANY {
            description
             "The gRPC daemon should listen on any address
              bound to an interface on the system.";
          }
        }
      }
      description
        "The IP addresses that the gRPC server should listen
        on. This may be an IPv4 or an IPv6 address";
    }
  }

  grouping system-grpc-server-top {
    description
      "Top-level grouping for system gRPC server data";

      container grpc-server {
        description
          "Top-level container for the gRPC server";

      container config {
        description
          "Configuration data for the system gRPC server";

        uses system-grpc-server-config;
      }

      container state {
        config false;

        description
          "Operational state data for the system gRPC server";

        uses system-grpc-server-config;
      }
    }
  }

  // data definition statements

  // augment statements

  // rpc statements

  // notification statements

}
